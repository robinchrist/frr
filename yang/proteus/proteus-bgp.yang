module proteus-bgp {
  yang-version 1.1;
  namespace "https://github.com/robinchrist/frr-proteus/yang/custom/bgp";
  prefix proteus-bgp;

  import ietf-inet-types {
    prefix inet;
  }
  import ietf-yang-types {
    prefix yang;
  }
  import proteus-types {
    prefix pt;
  }
  import proteus-bfd {
    prefix bfd;
  }
  import proteus-bgp-evpn {
    prefix evpn;
  }
  import proteus-bgp-filter {
    prefix bgpfilter;
  }
  import frr-route-map {
    prefix frr-route-map;
  }
  import frr-filter {
    prefix frr-filter;
  }
  import frr-interface {
    prefix frr-interface;
  }

  organization
    "frr-proteus";
  contact
    "https://github.com/robinchrist/frr-proteus";
  description
    "Self-contained configuration model for FRR bgpd, replacing FRR's
     own frr-bgp.yang module stack as frr-proteus's input schema.

     Why a rewrite instead of reusing FRR's model: frr-bgp.yang and its
     satellites are written almost entirely as 'augment' statements
     onto frr-routing's generic control-plane-protocol list, with the
     actual node definitions scattered across a dozen grouping files
     -- the tree a user actually configures is invisible in any single
     file. This module states the whole configuration tree directly,
     top-down, in one place (with EVPN's field definitions split into
     proteus-bgp-evpn.yang, pulled in with plain import + uses -- never
     'augment'). Policy-attachment names (route-map, prefix-list,
     access-list, AS-path filter-list, distribute-list) are lax
     inline leafrefs (require-instance false) into the owning modules
     (frr-route-map and frr-filter's lib containers, proteus-bgp-filter
     for AS-path lists): the leafref documents the target list, but its
     existence is not enforced. bgpd itself accepts a policy attachment
     whose object is not yet (or no longer) defined -- an operator can
     name a route-map before creating it, and deleting a route-map that
     a neighbor still references leaves the attachment in place until
     the map returns. A strict (require-instance true) leafref would
     reject those legitimate sequences, so the reference is kept lax to
     match the daemon. Interface-name references (update-source,
     source-interface, unnumbered neighbor addresses, flowspec
     local-install) are lax leafrefs for the same reason: they
     routinely name kernel interfaces that have no 'interface' config
     stanza at all.

     Coverage: the full config surface that bgpd's own
     bgp_config_write() emits (bgpd/bgp_vty.c), i.e. everything the
     'router bgp' CLI tree can persist, with these deliberate
     exclusions (each also marked where it would appear):
     - SRv6: CONVERTING in M8.5 (2026-07-19 ruling). The
       segment-routing-srv6 block is modeled below (B-srv6-block);
       sid vpn export, per-AF 'sid export' and the
       encapsulation-srv6 neighbor knobs follow in the M8.5 train.
     - 'rt|rt6 redirect import' (flowspec redirect, the tail of
       bgp_vpn_policy_config_write_afi) -- excluded together with the
       flowspec address family. The rest of that function's MPLS
       L3VPN leaking detail block (rd/label/nexthop vpn export, rt
       and route-map vpn import/export, import vrf route-map) IS
       modeled in the af-vpn-leaking grouping.
     - Address families encap, flowspec, unreachability and
       link-state, plus their per-family extras (pbr, distribute
       bgp-fabric-link-state, retain route-target for encap).
     - RPKI cache configuration (bgp_rpki.c), BMP (bgp_bmp.c), VNC,
       SNMP notifications, conditional 'bgp snmp traps' -- separate
       subsystems with their own config-write hooks.
     - The hidden 'view' semantics beyond declaring the type. (asdot
       AS values and the per-instance 'as-notation' display mode ARE
       modeled: pt:as-number is a plain-decimal/asdot union, and the
       instance carries an as-notation leaf.)
     - dynamic (listen-range) peers hold no config of their own; the
       listen ranges live under the peer-group they bind to.

     Structural departures from FRR's YANG, kept from the initial
     revision: no control-plane-protocol wrapper (root is
     a top-level /instance list keyed by VRF); address families are nested
     containers under 'afi-safis', not an identityref-keyed list;
     neighbor remote-as is one node mirroring the single CLI token
     (a choice between a structured plain/asdot ASN and the
     relationship keywords), not FRR's remote-as-type + remote-as
     pair.

     Semantics shared with the rest of the project: an unset leaf
     means 'not explicitly configured' and produces no config text --
     including knobs whose FRR default is 'on', where setting the leaf
     to false renders the explicit 'no ...' form (each such leaf says
     so). YANG defaults below document FRR's behavior but are not
     applied by the generated bindings (--no-dataclass-defaults).
     Every leaf corresponds to CLI text confirmed in bgpd's config
     write path (bgp_config_write / bgp_config_write_peer_global /
     bgp_config_write_peer_af / bgp_config_write_filter in bgp_vty.c,
     bgp_config_write_network / _redistribute / _distance in
     bgp_route.c, bgp_config_write_damp in bgp_damp.c,
     bgp_bfd_peer_config_write in bgp_bfd.c); numeric ranges come from
     the corresponding DEFPY grammars. Do not add leaves whose CLI
     rendering has not been verified there.";

  revision 2026-07-19 {
    description
      "Move the bgpd-owned interface-level 'mpls bgp ...' flags here,
       as an augment of frr-interface's interface list (they were
       modeled in the standalone proteus-interface module, now left
       unreferenced), and drop the proteus-interface import.";
  }
  revision 2026-07-05 {
    description
      "Initial revision (step 1 scope), then expanded the same day to
       the full bgp_config_write surface: process-level options,
       instance-level policy/timer/bestpath/GR knobs, peer-groups,
       the complete neighbor session and per-AF surface, and per-AF
       network/aggregate/redistribute/distance/dampening.";
  }

  /*
   * Session-level (not per-address-family) neighbor settings.
   * Shared verbatim between real neighbors and peer-groups: in FRR a
   * peer-group is configured with exactly the same 'neighbor PGNAME
   * ...' commands, and members inherit anything they don't override.
   */
  grouping neighbor-session-parameters {
    description
      "Per-session neighbor settings ('neighbor X ...' lines at
       'router bgp' level). Source: bgp_config_write_peer_global()
       in bgpd/bgp_vty.c.";

    container remote-as {
      description
        "'neighbor X remote-as <ASN|internal|external|auto>': one CLI
         token, three shapes -- a plain or asdot ASN (structured, see
         pt:as-number-notation) or a relationship keyword. Not
         mandatory in YANG because a peer-group member may inherit it
         from the group -- but FRR rejects any other neighbor
         configuration until a neighbor has remote-as from somewhere.
         // This grouping is shared with peer-group, so the
         // conditional-mandatory rule lives as a 'must' on the
         // neighbor list itself (validate_tree-enforced).";
      choice spec {
        description
          "Explicit ASN (either notation) or relationship keyword.
           The plain/asdot cases mirror pt:as-number-notation; they
           are spelled out here because YANG cannot extend a
           grouping's choice with an extra case.";

        case plain {
          leaf plain {
            type pt:as-number;
            description
              "Plain 32-bit decimal ASN.";
          }
        }
        case asdot {
          uses pt:asdot-as-number;
        }
        case type {
          leaf type {
            type enumeration {
              enum internal {
                description
                  "iBGP: peer must be in the local AS.";
              }
              enum external {
                description
                  "eBGP: peer must be outside the local AS.";
              }
              enum auto {
                description
                  "Accept either; sort out the relationship from the
                   OPEN message.";
              }
            }
            description
              "Relationship keyword instead of an explicit ASN.";
          }
        }
      }
    }

    container local-as {
      description
        "'neighbor X local-as ASN [no-prepend] [replace-as]
         [dual-as]': present a different AS to this peer. The ASN is
         the plain/asdot choice pulled in from
         pt:as-number-notation.";
      uses pt:as-number-notation;
      leaf no-prepend {
        type boolean;
        default "false";
        description
          "Do not prepend the local-as to routes received from the
           peer.";
      }
      leaf replace-as {
        type boolean;
        default "false";
        description
          "Replace (not prepend to) the real AS in updates sent to
           the peer.";
      }
      leaf dual-as {
        type boolean;
        default "false";
        description
          "Accept sessions addressed to either the local-as or the
           real AS.";
      }
    }

    leaf description {
      type string;
      description
        "'neighbor X description LINE'.";
    }

    container administrative-shutdown {
      description
        "Administrative shutdown of the session.";
      leaf enabled {
        type boolean;
        default "false";
        description
          "'neighbor X shutdown'.";
      }
      leaf message {
        type string;
        description
          "'neighbor X shutdown message MSG...': sent in the CEASE
           notification.";
      }
      container rtt {
        description
          "'neighbor X shutdown rtt (1-65535) [count (1-255)]':
           shut the session down automatically when its round-trip
           time exceeds the threshold.";
        leaf threshold {
          type uint16 {
            range "1..65535";
          }
          units "milliseconds";
        }
        leaf count {
          type uint8 {
            range "1..255";
          }
          description
            "Number of keepalive rounds the RTT must exceed the
             threshold before shutting down.";
        }
      }
    }

    container bfd {
      description
        "BFD liveness tracking for the session.";
      leaf enabled {
        type boolean;
        default "false";
        description
          "'neighbor X bfd'.";
      }
      leaf detect-multiplier {
        type uint8 {
          range "2..255";
        }
        default "3";
        description
          "'neighbor X bfd (2-255) (50-60000) (50-60000)': detection
           multiplier for the session.";
      }
      leaf min-rx {
        type uint32 {
          range "50..60000";
        }
        default "300";
        description
          "'neighbor X bfd (2-255) (50-60000) (50-60000)': required
           minimum receive interval, in milliseconds.";
      }
      leaf min-tx {
        type uint32 {
          range "50..60000";
        }
        default "300";
        description
          "'neighbor X bfd (2-255) (50-60000) (50-60000)': desired
           minimum transmit interval, in milliseconds.";
      }
      leaf check-control-plane-failure {
        type boolean;
        default "false";
        description
          "'neighbor X bfd check-control-plane-failure': also allow
           BFD down events caused by control-plane restarts to reset
           the session.";
      }
      leaf profile {
        /* LIMITATION: this is intentionally a plain string and NOT a
           leafref to /bfd:profile/bfd:name. BFD profiles are configured
           in the separate BFD subsystem and are not present in this
           datastore, so a leafref's require-instance check can never be
           satisfied here and would reject every valid profile name. The
           trade-off is that referential integrity is lost: a name that
           does not match any configured BFD profile is accepted at
           validation time (matching the legacy behaviour, which stored
           the name verbatim without checking it exists). */
        type string;
        description
          "'neighbor X bfd profile BFDPROF': name of the BFD profile to
           apply to the session. The profile is defined separately in
           the BFD configuration; its existence is NOT validated here
           (see the LIMITATION comment on this leaf), so a name with no
           matching BFD profile is accepted.";
      }
      leaf strict {
        type boolean;
        default "false";
        description
          "'neighbor X bfd strict': keep the session from coming up
           until the BFD session is up.";
      }
      leaf strict-hold-time {
        type uint32 {
          range "1..4294967295";
        }
        description
          "'neighbor X bfd strict hold-time (1-4294967295)': seconds to
           wait for the BFD session to come up, in strict mode, before
           declaring it down.";
      }
    }

    leaf password {
      type string;
      description
        "'neighbor X password PASSWORD': TCP MD5 authentication.";
    }

    leaf solo {
      type boolean;
      default "false";
      description
        "'neighbor X solo': do not reflect routes back that were
         learned from this peer.";
    }

    leaf port {
      type uint16;
      description
        "'neighbor X port (0-65535)': non-default TCP port.";
    }

    leaf source-interface {
      // Inline leafref with require-instance false on purpose (C.4 test,
      // libyang, 2026-07-19): a strict interface ref rejects a name that
      // is a real kernel interface with no 'interface' config stanza -
      // a real workflow for this knob.
      type leafref {
        path "/frr-interface:lib/frr-interface:interface/frr-interface:name";
        require-instance false;
      }
      description
        "'neighbor X interface IFNAME' (peer->ifname, the 'Local
         interface name' line in bgp_config_write_peer_global). Note
         this is a legacy knob distinct from update-source and from
         unnumbered interface peers. Lax leafref into frr-interface
         (require-instance false): interface names that have no
         'interface' config stanza -- plain kernel interfaces -- must
         remain acceptable here, so the reference documents the
         target without demanding a configured instance.";
    }

    leaf tcp-mss {
      type uint16 {
        range "1..65535";
      }
      description
        "'neighbor X tcp-mss (1-65535)'.";
    }

    leaf passive {
      type boolean;
      default "false";
      description
        "'neighbor X passive': never open the connection, only
         accept.";
    }

    leaf ebgp-multihop {
      type uint8 {
        range "1..255";
      }
      description
        "'neighbor X ebgp-multihop [(1-255)]': allow eBGP over
         multiple hops with this TTL. 255 renders as the bare
         'ebgp-multihop' form (that is how FRR writes MAXTTL back).";
    }

    leaf aigp {
      type boolean;
      default "false";
      description
        "'neighbor X aigp': send/receive the AIGP attribute.";
    }

    leaf graceful-shutdown {
      type boolean;
      default "false";
      description
        "'neighbor X graceful-shutdown' (RFC 8326 per-peer).";
    }

    container local-role {
      description
        "'neighbor X local-role
         <provider|rs-server|rs-client|customer|peer> [strict-mode]'
         (RFC 9234 roles).";
      leaf role {
        type enumeration {
          enum provider;
          enum rs-server;
          enum rs-client;
          enum customer;
          enum peer;
        }
      }
      leaf strict-mode {
        type boolean;
        default "false";
        description
          "Refuse the session if the peer does not announce a
           matching role.";
      }
    }

    leaf oad {
      type boolean;
      default "false";
      description
        "'neighbor X oad': treat this eBGP session as
         One-Administrative-Domain (draft-ietf-idr-bgp-ct /
         BGP_PEER_EBGP_OAD sub-sort).";
    }

    leaf ttl-security-hops {
      type uint8 {
        range "1..254";
      }
      must "not(../ebgp-multihop)" {
        error-message
          "ttl-security hops and ebgp-multihop are mutually
           exclusive";
      }
      description
        "'neighbor X ttl-security hops (1-254)' (GTSM, RFC 5082).
         Mutually exclusive with ebgp-multihop in FRR (the 'must').";
    }

    leaf connected-check {
      type boolean;
      default "true";
      description
        "'neighbor X connected-check <enabled|disabled>': when enabled,
         the directly-connected check is enforced for single-hop eBGP;
         when disabled, single-hop eBGP to a non-connected address is
         allowed without ebgp-multihop (default enabled).";
    }

    leaf enforce-first-as {
      type boolean;
      description
        "'neighbor X enforce-first-as' / 'no neighbor X
         enforce-first-as'. Three-valued: unset inherits the
         instance-level setting; true/false render the explicit
         positive/negative form when they differ from it.";
    }

    leaf update-source {
      type union {
        type inet:ip-address-no-zone;
        // Interface-name branch: lax leafref (require-instance false) per
        // the C.4 test (libyang, 2026-07-19) - kernel interfaces without
        // an 'interface' config stanza must remain accepted.
        type leafref {
          path "/frr-interface:lib/frr-interface:interface/frr-interface:name";
          require-instance false;
        }
      }
      description
        "'neighbor X update-source <A.B.C.D|X:X::X:X|IFNAME>'.
         The interface-name branch is a lax leafref
         (require-instance false): update-source routinely names
         kernel interfaces that have no 'interface' config stanza,
         and those must remain acceptable.";
    }

    leaf ip-transparent {
      type boolean;
      default "false";
      description
        "'neighbor X ip-transparent': source the TCP connection from
         a foreign/transparent address.";
    }

    leaf ls-local-link-id {
      type uint32 {
        range "1..4294967295";
      }
      description
        "'neighbor X local-link-id (1-4294967295)': pin the BGP-LS
         local link identifier for the link NLRI describing this
         session (M9; the fallback is the kernel ifindex).";
    }

    leaf ls-remote-link-id {
      type uint32 {
        range "1..4294967295";
      }
      description
        "'neighbor X remote-link-id (1-4294967295)': pin the BGP-LS
         remote link identifier.";
    }

    leaf advertisement-interval {
      type uint16 {
        range "0..600";
      }
      units "seconds";
      description
        "'neighbor X advertisement-interval (0-600)' (MRAI).";
    }

    container timers {
      description
        "Per-neighbor session timers.";
      leaf keepalive {
        type uint16;
        units "seconds";
        must "../holdtime" {
          error-message
            "'neighbor X timers' takes keepalive and holdtime
             together";
        }
        description
          "First argument of 'neighbor X timers (0-65535) (0-65535)'.";
      }
      leaf holdtime {
        type uint16;
        units "seconds";
        must "../keepalive" {
          error-message
            "'neighbor X timers' takes keepalive and holdtime
             together";
        }
        description
          "Second argument of 'neighbor X timers'. Set both or
           neither -- one CLI line (the 'must' pair).";
      }
      leaf connect {
        type uint16 {
          range "1..65535";
        }
        units "seconds";
        description
          "'neighbor X timers connect (1-65535)': connect retry
           interval.";
      }
      leaf delayopen {
        type uint8 {
          range "1..240";
        }
        units "seconds";
        description
          "'neighbor X timers delayopen (1-240)' (RFC 4271
           DelayOpenTimer).";
      }
    }

    container capabilities {
      description
        "Capability negotiation knobs. The three-valued booleans here
         follow the same convention as enforce-first-as: unset =
         inherit the instance-level 'bgp default ...' setting, and
         the explicit form is rendered only on mismatch.";
      leaf dynamic {
        type boolean;
        description
          "'[no] neighbor X capability dynamic'.";
      }
      leaf extended-nexthop {
        type boolean;
        description
          "'[no] neighbor X capability extended-nexthop' (RFC 8950;
           implied on for unnumbered interface peers).";
      }
      leaf software-version {
        type boolean;
        description
          "'[no] neighbor X capability software-version'.";
      }
      leaf software-version-latest-encoding {
        type boolean;
        description
          "'[no] neighbor X capability software-version
           latest-encoding'.";
      }
      leaf link-local {
        type boolean;
        description
          "'[no] neighbor X capability link-local'.";
      }
      leaf fqdn {
        type boolean;
        description
          "'no neighbor X capability fqdn' when false. FRR's default
           is on and only the negative form is ever written.";
      }
      leaf dont-capability-negotiate {
        type boolean;
        default "false";
        description
          "'neighbor X dont-capability-negotiate'.";
      }
      leaf override-capability {
        type boolean;
        default "false";
        description
          "'neighbor X override-capability': ignore the peer's
           capability announcement entirely.";
      }
      leaf strict-capability-match {
        type boolean;
        default "false";
        must "../override-capability != 'true'" {
          error-message
            "Can't set override-capability and strict-capability-match at
             the same time";
        }
        description
          "'neighbor X strict-capability-match'. Mutually exclusive with
           override-capability in FRR (the 'must'; peer_flag_modify()'s
           own BGP_ERR_PEER_FLAG_CONFLICT check, bgpd.c).";
      }
    }

    leaf rpki-strict {
      type boolean;
      default "false";
      description
        "'neighbor X rpki strict'.
         // The RPKI cache-server configuration itself (bgp_rpki.c)
         // is not modeled; this per-peer flag is independent of it.";
    }

    leaf sender-as-path-loop-detection {
      type boolean;
      default "false";
      description
        "'neighbor X sender-as-path-loop-detection': do not send
         routes whose AS path already contains the peer's AS.";
    }

    leaf-list path-attribute-discard {
      type uint8 {
        range "1..255";
      }
      description
        "'neighbor X path-attribute discard (1-255)...': BGP path
         attribute type codes to silently discard on receipt.";
    }

    leaf-list path-attribute-treat-as-withdraw {
      type uint8 {
        range "1..255";
      }
      description
        "'neighbor X path-attribute treat-as-withdraw (1-255)...'.";
    }

    leaf graceful-restart-mode {
      type enumeration {
        enum restarter {
          description
            "'neighbor X graceful-restart'.";
        }
        enum helper {
          description
            "'neighbor X graceful-restart-helper'.";
        }
        enum disable {
          description
            "'neighbor X graceful-restart-disable'.";
        }
      }
      description
        "Per-neighbor graceful-restart role override; unset inherits
         the instance-level mode.";
    }

    leaf send-nexthop-characteristics {
      type boolean;
      default "false";
      description
        "'neighbor X send-nexthop-characteristics' (NHC attribute).";
    }

    leaf link-bw-encoding-ieee {
      type boolean;
      default "true";
      description
        "'neighbor X link-bw-encoding-ieee <enabled|disabled>': when
         enabled, link bandwidth in extended communities is encoded in
         IEEE floating-point format; when disabled, the legacy uint32
         encoding is used for backward compatibility (default
         enabled).";
    }

    leaf extended-link-bandwidth {
      type boolean;
      default "false";
      description
        "'neighbor X extended-link-bandwidth' (IPv6-address-specific
         link bandwidth communities, > 25 Gbps capable).";
    }

    leaf extended-optional-parameters {
      type boolean;
      default "false";
      description
        "'neighbor X extended-optional-parameters' (RFC 9072
         extended OPEN encoding, normally auto-detected).";
    }
  }

  /*
   * Per-address-family neighbor settings. One grouping for all
   * families: FRR installs most of these commands in every AF node
   * and the written text is identical; the few knobs that are
   * meaningless in some family (e.g. ORF under l2vpn evpn) are simply
   * never emitted by FRR there -- we do not restrict per family.
   */
  grouping neighbor-af-encap-unicast {
    description
      "'neighbor X <encapsulation-srv6|encapsulation-srv6-relax>'
       (unicast AFs, M8.5 B-srv6-unicast): advertise routes with an
       SRv6 prefix SID to this peer (relax = with and without). One
       enum leaf - the two legacy flags are mutually exclusive, so a
       direct switch is a single modify (legacy's unset-first
       requirement is dropped).";

    leaf encapsulation {
      type enumeration {
        enum srv6;
        enum srv6-relax;
      }
      description
        "SRv6 encapsulation advertisement mode; absent = disabled.";
    }
  }

  grouping neighbor-af-encap-vpn {
    description
      "'neighbor X <encapsulation-srv6|encapsulation-mpls>'
       (vpn AFs, M8.5): two independent Tier A booleans, both may be
       set (bgp_vty.c neighbor_encapsulation_srv6_or_mpls_cmd).";

    leaf encapsulation-srv6 {
      type boolean;
      default "false";
      description
        "Advertise VPN routes with SRv6 encapsulation.";
    }

    leaf encapsulation-mpls {
      type boolean;
      default "false";
      description
        "Advertise VPN routes with MPLS encapsulation.";
    }
  }

  grouping neighbor-af-flowspec {
    description
      "Per-neighbor settings of a flowspec address-family (M8.5
       B-fs-af): exactly the nine arms the legacy flowspec nodes
       installed - activate, soft-reconfiguration inbound,
       attribute-unchanged, route-reflector-client,
       route-server-client, and the prefix-list / filter-list /
       route-map filters. Deliberately NOT 'uses neighbor-af': the
       broad grouping would model per-AF knobs the flowspec CLI
       never offered.";

    leaf activate {
      type boolean;
      default "false";
      description
        "'neighbor X activate' for this flowspec AF.";
    }

    leaf soft-reconfiguration-inbound {
      type boolean;
      default "false";
      description
        "'neighbor X soft-reconfiguration inbound'.";
    }

    container attribute-unchanged {
      description
        "'neighbor X attribute-unchanged [as-path|next-hop|med]'.";

      leaf as-path {
        type boolean;
        default "false";
      }
      leaf next-hop {
        type boolean;
        default "false";
      }
      leaf med {
        type boolean;
        default "false";
      }
    }

    leaf route-reflector-client {
      type boolean;
      default "false";
      description
        "'neighbor X route-reflector-client'.";
    }

    leaf route-server-client {
      type boolean;
      default "false";
      description
        "'neighbor X route-server-client'.";
    }

    container filters {
      description
        "Flowspec per-peer filters.";

      leaf prefix-list-in {
        // Inline leafref, kept lax (require-instance false, see header).
        // Not reusing frr-filter's prefix-list-ref - that typedef is
        // require-instance false and shared with other daemons.
        // frr-filter keys prefix-lists by "type name", so this leafref
        // matches the name in any address family; family precision is not
        // enforced (legacy-equivalent).
        type leafref {
          path "/frr-filter:lib/frr-filter:prefix-list/frr-filter:name";
          require-instance false;
        }
      }
      leaf prefix-list-out {
        // Inline leafref, kept lax (require-instance false, see header).
        // Not reusing frr-filter's prefix-list-ref - that typedef is
        // require-instance false and shared with other daemons.
        // frr-filter keys prefix-lists by "type name", so this leafref
        // matches the name in any address family; family precision is not
        // enforced (legacy-equivalent).
        type leafref {
          path "/frr-filter:lib/frr-filter:prefix-list/frr-filter:name";
          require-instance false;
        }
      }
      leaf filter-list-in {
        // Inline leafref, kept lax (require-instance false, see header).
        // The target list is BGP-owned (proteus-bgp-filter), so there is no
        // shared lax typedef to avoid and strict affects bgpd only.
        type leafref {
          path "/bgpfilter:as-path-access-list/bgpfilter:name";
          require-instance false;
        }
      }
      leaf filter-list-out {
        // Inline leafref, kept lax (require-instance false, see header).
        // The target list is BGP-owned (proteus-bgp-filter), so there is no
        // shared lax typedef to avoid and strict affects bgpd only.
        type leafref {
          path "/bgpfilter:as-path-access-list/bgpfilter:name";
          require-instance false;
        }
      }
      leaf route-map-in {
        // Inline leafref, kept lax (require-instance false, see header).
        // Not reusing frr-route-map:route-map-ref - that typedef is
        // require-instance false and shared with other daemons.
        type leafref {
          path "/frr-route-map:lib/frr-route-map:route-map/frr-route-map:name";
          require-instance false;
        }
      }
      leaf route-map-out {
        // Inline leafref, kept lax (require-instance false, see header).
        // Not reusing frr-route-map:route-map-ref - that typedef is
        // require-instance false and shared with other daemons.
        type leafref {
          path "/frr-route-map:lib/frr-route-map:route-map/frr-route-map:name";
          require-instance false;
        }
      }
    }
  }

  grouping neighbor-af-unreachability {
    description
      "Per-neighbor settings of an unreachability address-family
       (M9): exactly the arms the legacy unreachability nodes
       installed - activate, route-map filters, the maximum-prefix
       family, maximum-prefix-out and allowas-in. Deliberately NOT
       'uses neighbor-af': the broad grouping would model per-AF
       knobs the unreachability CLI never offered.";

    leaf activate {
      type boolean;
      default "false";
      description
        "'neighbor X activate' for this unreachability AF.";
    }

    container maximum-prefix {
      description
        "'neighbor X maximum-prefix (1-4294967295) [(1-100)]
         [restart (1-65535)] [warning-only] [force]'.";
      leaf count {
        type uint32 {
          range "1..4294967295";
        }
        description
          "Prefix limit; the rest of this container is meaningless
           without it.";
      }
      leaf threshold {
        type uint8 {
          range "1..100";
        }
        units "percent";
        description
          "Warn at this percentage of the limit (FRR default 75,
           which it does not write back).";
      }
      leaf warning-only {
        type boolean;
        default "false";
        description
          "Log instead of tearing the session down.";
      }
      leaf restart-interval {
        type uint16 {
          range "1..65535";
        }
        units "minutes";
        description
          "Re-establish automatically after this interval.";
      }
      leaf force {
        type boolean;
        default "false";
        description
          "Count all received prefixes, not just accepted ones
           (needs soft-reconfiguration inbound).";
      }
    }

    leaf maximum-prefix-out {
      type uint32 {
        range "1..4294967295";
      }
      description
        "'neighbor X maximum-prefix-out (1-4294967295)'.";
    }

    container allowas-in {
      description
        "'neighbor X allowas-in [<(1-10)|origin>]' and
         'neighbor X allowas-in route-map NAME [<(1-10)|origin>]':
         accept routes containing our own AS. Bare 'allowas-in'
         (count unset, origin false) means FRR's default of 3.";
      leaf enabled {
        type boolean;
        default "false";
      }
      leaf count {
        type uint8 {
          range "1..10";
        }
        description
          "Maximum own-AS occurrences.";
      }
      leaf origin {
        type boolean;
        default "false";
        must ". = 'false' or not(../count)" {
          error-message
            "allowas-in origin and count are mutually exclusive";
        }
        description
          "Only accept if our AS is the origin. Mutually exclusive
           with count -- one CLI slot (the 'must').";
      }
      leaf route-map {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "Restrict allowas-in to routes the route-map permits.";
      }
    }

    container filters {
      description
        "Unreachability per-peer filters.";

      leaf route-map-in {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "'neighbor X route-map NAME in'.";
      }
      leaf route-map-out {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "'neighbor X route-map NAME out'.";
      }
    }
  }

  grouping neighbor-af-link-state {
    description
      "Per-neighbor settings of the link-state address-family (M9):
       exactly the arms the legacy BGP_LS_NODE installed - activate
       and the route-map filters.";

    leaf activate {
      type boolean;
      default "false";
      description
        "'neighbor X activate' for the link-state AF.";
    }

    container filters {
      description
        "Link-state per-peer filters.";

      leaf route-map-in {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "'neighbor X route-map NAME in'.";
      }
      leaf route-map-out {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "'neighbor X route-map NAME out'.";
      }
    }
  }

  grouping neighbor-af {
    description
      "Per-neighbor settings inside an 'address-family' block
       ('neighbor X ...' lines at AF level). Source:
       bgp_config_write_peer_af() + bgp_config_write_filter() in
       bgpd/bgp_vty.c, bgp_config_write_peer_damp() in bgp_damp.c.";

    leaf activate {
      type boolean;
      description
        "'neighbor X activate' / 'no neighbor X activate'.
         Three-valued: unset follows FRR's per-AF default activation
         ('bgp default ipv4-unicast' & friends -- on by default only
         for ipv4-unicast); true/false force the explicit form.";
    }

    container addpath {
      description
        "ADD-PATH (RFC 7911) knobs.";
      leaf tx {
        type enumeration {
          enum all-paths {
            description
              "'neighbor X addpath-tx-all-paths'.";
          }
          enum best-per-as {
            description
              "'neighbor X addpath-tx-bestpath-per-AS'.";
          }
          enum best-selected {
            description
              "'neighbor X addpath-tx-best-selected (1-6)'; the count
               lives in tx-best-selected.";
          }
        }
        description
          "Which paths to advertise with ADD-PATH.";
      }
      leaf tx-best-selected {
        type uint8 {
          range "1..6";
        }
        must "../tx = 'best-selected'" {
          error-message
            "tx-best-selected requires tx = best-selected";
        }
        description
          "Path count for tx = best-selected; meaningless (and
           rejected by the 'must') otherwise.";
      }
      leaf rx {
        type boolean;
        default "true";
        description
          "'neighbor X addpath-rx <enabled|disabled>': when enabled,
           additional paths are accepted from the neighbor; when
           disabled, they are not (default enabled).";
      }
      leaf rx-paths-limit {
        type uint16 {
          range "1..65535";
        }
        description
          "'neighbor X addpath-rx-paths-limit (1-65535)'
           (paths-limit capability,
           draft-ietf-idr-addpath-paths-limit).";
      }
    }

    leaf orf-prefix-list {
      type enumeration {
        enum send;
        enum receive;
        enum both;
      }
      description
        "'neighbor X capability orf prefix-list
         <send|receive|both>'.";
    }

    leaf route-reflector-client {
      type boolean;
      default "false";
      description
        "'neighbor X route-reflector-client'. iBGP neighbors only.";
    }

    container next-hop-self {
      description
        "'neighbor X next-hop-self [force]'. FRR writes 'force' as a
         separate line; both leaves may be set.";
      leaf enabled {
        type boolean;
        default "false";
      }
      leaf force {
        type boolean;
        default "false";
        description
          "Also self-source routes reflected from other iBGP peers.";
      }
    }

    leaf remove-private-as {
      type enumeration {
        enum basic {
          description
            "'neighbor X remove-private-AS': strip private ASNs if
             the path contains only private ASNs.";
        }
        enum all {
          description
            "'neighbor X remove-private-AS all'.";
        }
        enum replace-as {
          description
            "'neighbor X remove-private-AS replace-AS'.";
        }
        enum all-replace-as {
          description
            "'neighbor X remove-private-AS all replace-AS'.";
        }
      }
      description
        "Private-AS scrubbing on advertisements to this peer.";
    }

    leaf as-override {
      type boolean;
      default "false";
      description
        "'neighbor X as-override': replace the peer's AS with our own
         in advertisements.";
    }

    container send-community {
      description
        "Community propagation. FRR sends all community flavors by
         default and only writes the 'no neighbor X send-community
         <standard|extended|large|all>' negations, so these leaves are
         three-valued: unset = FRR default (send), false = render the
         'no' form. extended-rpki is the exception: off by default,
         written positively.";
      leaf standard {
        type boolean;
      }
      leaf extended {
        type boolean;
      }
      leaf large {
        type boolean;
      }
      leaf extended-rpki {
        type boolean;
        default "false";
        description
          "'neighbor X send-community extended rpki' (RFC 8097 origin
           validation state).";
      }
    }

    container default-originate {
      description
        "'neighbor X default-originate [route-map NAME]'.";
      leaf enabled {
        type boolean;
        default "false";
      }
      leaf route-map {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "Advertise the default only if the route-map permits.";
      }
    }

    leaf soft-reconfiguration-inbound {
      type boolean;
      default "false";
      description
        "'neighbor X soft-reconfiguration inbound'.";
    }

    container maximum-prefix {
      description
        "'neighbor X maximum-prefix (1-4294967295) [(1-100)]
         [restart (1-65535)] [warning-only] [force]'.";
      leaf count {
        type uint32 {
          range "1..4294967295";
        }
        description
          "Prefix limit; the rest of this container is meaningless
           without it.";
      }
      leaf threshold {
        type uint8 {
          range "1..100";
        }
        units "percent";
        description
          "Warn at this percentage of the limit (FRR default 75,
           which it does not write back).";
      }
      leaf warning-only {
        type boolean;
        default "false";
        description
          "Log instead of tearing the session down.";
      }
      leaf restart-interval {
        type uint16 {
          range "1..65535";
        }
        units "minutes";
        description
          "Re-establish automatically after this interval.";
      }
      leaf force {
        type boolean;
        default "false";
        description
          "Count all received prefixes, not just accepted ones
           (needs soft-reconfiguration inbound).";
      }
    }

    leaf maximum-prefix-out {
      type uint32 {
        range "1..4294967295";
      }
      description
        "'neighbor X maximum-prefix-out (1-4294967295)'.";
    }

    leaf route-server-client {
      type boolean;
      default "false";
      description
        "'neighbor X route-server-client'.";
    }

    leaf nexthop-local-unchanged {
      type boolean;
      default "false";
      description
        "'neighbor X nexthop-local unchanged': keep the link-local
         next hop instead of rewriting it.";
    }

    container allowas-in {
      description
        "'neighbor X allowas-in [<(1-10)|origin>]' and
         'neighbor X allowas-in route-map NAME [<(1-10)|origin>]':
         accept routes containing our own AS. Bare 'allowas-in'
         (count unset, origin false) means FRR's default of 3.";
      leaf enabled {
        type boolean;
        default "false";
      }
      leaf count {
        type uint8 {
          range "1..10";
        }
        description
          "Maximum own-AS occurrences.";
      }
      leaf origin {
        type boolean;
        default "false";
        must ". = 'false' or not(../count)" {
          error-message
            "allowas-in origin and count are mutually exclusive";
        }
        description
          "Only accept if our AS is the origin. Mutually exclusive
           with count -- one CLI slot (the 'must').";
      }
      leaf route-map {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "Restrict allowas-in to routes the route-map permits.";
      }
    }

    leaf accept-own {
      type boolean;
      default "false";
      description
        "'neighbor X accept-own' (RFC 7611 ACCEPT_OWN community;
         VPN families).";
    }

    container soo {
      description
        "'neighbor X soo ASN:NN_OR_IP-ADDRESS:NN': site-of-origin
         extended community stamped on routes from this peer. A Route
         Origin (RFC 4360 subtype 0x03) -- deliberately NOT the
         route-target grouping, which is a different extended
         community (subtype 0x02).";
      presence "A site-of-origin is configured for routes from this
                peer.";
      uses pt:route-origin;
    }

    leaf weight {
      type uint16;
      description
        "'neighbor X weight (0-65535)'.";
    }

    /*
     * The 'filters' container is deliberately NOT part of this
     * grouping: it is split one grouping per address family so each
     * family's distribute-list/prefix-list CLI wording stays with its
     * own family. Every AF container pairs 'uses neighbor-af' with the
     * matching 'uses neighbor-af-filters-<family>' grouping (defined
     * right after this one).
     */

    container attribute-unchanged {
      description
        "'neighbor X attribute-unchanged [as-path] [next-hop] [med]':
         propagate these attributes unmodified.";
      leaf as-path {
        type boolean;
        default "false";
      }
      leaf next-hop {
        type boolean;
        default "false";
      }
      leaf med {
        type boolean;
        default "false";
      }
    }

    container dampening {
      must "not(reuse-threshold or suppress-threshold or max-suppress-time)
            or (half-life and reuse-threshold and suppress-threshold
                and max-suppress-time)" {
        error-message
          "dampening takes none of the numbers, only half-life, or
           all four";
      }
      description
        "'neighbor X dampening [(1-45) [(1-20000) (1-20000)
         (1-255)]]': per-neighbor route-flap dampening
         (bgp_config_write_peer_damp in bgp_damp.c). Either give none
         of the numbers, only half-life, or all four (the 'must').";
      leaf enabled {
        type boolean;
        default "false";
      }
      leaf half-life {
        type uint8 {
          range "1..45";
        }
        units "minutes";
      }
      leaf reuse-threshold {
        type uint16 {
          range "1..20000";
        }
      }
      leaf suppress-threshold {
        type uint16 {
          range "1..20000";
        }
      }
      leaf max-suppress-time {
        type uint8 {
          range "1..255";
        }
        units "minutes";
      }
    }
  }

  /*
   * The per-AF 'filters' container, one grouping per address family so
   * each family's distribute-list/prefix-list CLI wording stays with
   * its own family. The family-independent tail (AS-path filter-lists,
   * route-maps, conditional advertisement) lives in
   * neighbor-af-filters-common; l2vpn-evpn gets its own variant. All
   * policy-name leaves are plain strings (see the module description).
   */

  grouping neighbor-af-filters-common {
    description
      "Family-independent part of the per-AF 'filters' container
       (bgp_config_write_filter in bgpd/bgp_vty.c).";

    leaf filter-list-in {
      // Inline leafref, kept lax (require-instance false, see header).
      // The target list is BGP-owned (proteus-bgp-filter), so there is no
      // shared lax typedef to avoid and strict affects bgpd only.
      type leafref {
        path "/bgpfilter:as-path-access-list/bgpfilter:name";
        require-instance false;
      }
      description
        "'neighbor X filter-list NAME in' (AS-path filter).";
    }
    leaf filter-list-out {
      // Inline leafref, kept lax (require-instance false, see header).
      // The target list is BGP-owned (proteus-bgp-filter), so there is no
      // shared lax typedef to avoid and strict affects bgpd only.
      type leafref {
        path "/bgpfilter:as-path-access-list/bgpfilter:name";
        require-instance false;
      }
      description
        "'neighbor X filter-list NAME out'.";
    }
    leaf route-map-in {
      // Inline leafref, kept lax (require-instance false, see header).
      // Not reusing frr-route-map:route-map-ref - that typedef is
      // require-instance false and shared with other daemons.
      type leafref {
        path "/frr-route-map:lib/frr-route-map:route-map/frr-route-map:name";
        require-instance false;
      }
      description
        "'neighbor X route-map NAME in'.";
    }
    leaf route-map-out {
      // Inline leafref, kept lax (require-instance false, see header).
      // Not reusing frr-route-map:route-map-ref - that typedef is
      // require-instance false and shared with other daemons.
      type leafref {
        path "/frr-route-map:lib/frr-route-map:route-map/frr-route-map:name";
        require-instance false;
      }
      description
        "'neighbor X route-map NAME out'.";
    }
    leaf unsuppress-map {
      // Inline leafref, kept lax (require-instance false, see header).
      // Not reusing frr-route-map:route-map-ref - that typedef is
      // require-instance false and shared with other daemons.
      type leafref {
        path "/frr-route-map:lib/frr-route-map:route-map/frr-route-map:name";
        require-instance false;
      }
      description
        "'neighbor X unsuppress-map NAME': advertise
         aggregate-suppressed routes the map permits.";
    }
    container conditional-advertisement {
      description
        "'neighbor X advertise-map NAME <exist-map|non-exist-map>
         NAME' (conditional advertisement, always outbound).";
      leaf advertise-map {
        // Inline leafref, kept lax (require-instance false, see header).
        // Not reusing frr-route-map:route-map-ref - that typedef is
        // require-instance false and shared with other daemons.
        type leafref {
          path "/frr-route-map:lib/frr-route-map:route-map/frr-route-map:name";
          require-instance false;
        }
      }
      leaf condition {
        type enumeration {
          enum exist {
            description
              "Advertise while the condition-map matches something
               in the BGP table.";
          }
          enum non-exist {
            description
              "Advertise while it does not.";
          }
        }
      }
      leaf condition-map {
        // Inline leafref, kept lax (require-instance false, see header).
        // Not reusing frr-route-map:route-map-ref - that typedef is
        // require-instance false and shared with other daemons.
        type leafref {
          path "/frr-route-map:lib/frr-route-map:route-map/frr-route-map:name";
          require-instance false;
        }
      }
    }
  }

  grouping neighbor-af-filters-ipv4 {
    description
      "Per-AF 'filters' container for IPv4 address families.";

    container filters {
      must "not(distribute-list-in and prefix-list-in)" {
        error-message
          "distribute-list and prefix-list are mutually exclusive
           per direction (in)";
      }
      must "not(distribute-list-out and prefix-list-out)" {
        error-message
          "distribute-list and prefix-list are mutually exclusive
           per direction (out)";
      }
      description
        "Per-direction filtering (bgp_config_write_filter in
         bgpd/bgp_vty.c). Note FRR's 'one slot' rule: distribute-list
         and prefix-list are mutually exclusive per direction (the
         'must' pair).";
      leaf distribute-list-in {
        // Inline leafref, kept lax (require-instance false, see header).
        // Not reusing frr-filter's access-list-ref - that typedef is
        // require-instance false and shared with other daemons.
        // frr-filter keys access-lists by "type name", so this leafref
        // matches the name in any address family; family precision is not
        // enforced (legacy-equivalent).
        type leafref {
          path "/frr-filter:lib/frr-filter:access-list/frr-filter:name";
          require-instance false;
        }
        description
          "'neighbor X distribute-list NAME in'.";
      }
      leaf distribute-list-out {
        // Inline leafref, kept lax (require-instance false, see header).
        // Not reusing frr-filter's access-list-ref - that typedef is
        // require-instance false and shared with other daemons.
        // frr-filter keys access-lists by "type name", so this leafref
        // matches the name in any address family; family precision is not
        // enforced (legacy-equivalent).
        type leafref {
          path "/frr-filter:lib/frr-filter:access-list/frr-filter:name";
          require-instance false;
        }
        description
          "'neighbor X distribute-list NAME out'.";
      }
      leaf prefix-list-in {
        // Inline leafref, kept lax (require-instance false, see header).
        // Not reusing frr-filter's prefix-list-ref - that typedef is
        // require-instance false and shared with other daemons.
        // frr-filter keys prefix-lists by "type name", so this leafref
        // matches the name in any address family; family precision is not
        // enforced (legacy-equivalent).
        type leafref {
          path "/frr-filter:lib/frr-filter:prefix-list/frr-filter:name";
          require-instance false;
        }
        description
          "'neighbor X prefix-list NAME in'.";
      }
      leaf prefix-list-out {
        // Inline leafref, kept lax (require-instance false, see header).
        // Not reusing frr-filter's prefix-list-ref - that typedef is
        // require-instance false and shared with other daemons.
        // frr-filter keys prefix-lists by "type name", so this leafref
        // matches the name in any address family; family precision is not
        // enforced (legacy-equivalent).
        type leafref {
          path "/frr-filter:lib/frr-filter:prefix-list/frr-filter:name";
          require-instance false;
        }
        description
          "'neighbor X prefix-list NAME out'.";
      }
      uses neighbor-af-filters-common;
    }
  }

  grouping neighbor-af-filters-ipv6 {
    description
      "Per-AF 'filters' container for IPv6 address families.";

    container filters {
      must "not(distribute-list-in and prefix-list-in)" {
        error-message
          "distribute-list and prefix-list are mutually exclusive
           per direction (in)";
      }
      must "not(distribute-list-out and prefix-list-out)" {
        error-message
          "distribute-list and prefix-list are mutually exclusive
           per direction (out)";
      }
      description
        "Per-direction filtering (bgp_config_write_filter in
         bgpd/bgp_vty.c). Note FRR's 'one slot' rule: distribute-list
         and prefix-list are mutually exclusive per direction (the
         'must' pair).";
      leaf distribute-list-in {
        // Inline leafref, kept lax (require-instance false, see header).
        // Not reusing frr-filter's access-list-ref - that typedef is
        // require-instance false and shared with other daemons.
        // frr-filter keys access-lists by "type name", so this leafref
        // matches the name in any address family; family precision is not
        // enforced (legacy-equivalent).
        type leafref {
          path "/frr-filter:lib/frr-filter:access-list/frr-filter:name";
          require-instance false;
        }
        description
          "'neighbor X distribute-list NAME in'.";
      }
      leaf distribute-list-out {
        // Inline leafref, kept lax (require-instance false, see header).
        // Not reusing frr-filter's access-list-ref - that typedef is
        // require-instance false and shared with other daemons.
        // frr-filter keys access-lists by "type name", so this leafref
        // matches the name in any address family; family precision is not
        // enforced (legacy-equivalent).
        type leafref {
          path "/frr-filter:lib/frr-filter:access-list/frr-filter:name";
          require-instance false;
        }
        description
          "'neighbor X distribute-list NAME out'.";
      }
      leaf prefix-list-in {
        // Inline leafref, kept lax (require-instance false, see header).
        // Not reusing frr-filter's prefix-list-ref - that typedef is
        // require-instance false and shared with other daemons.
        // frr-filter keys prefix-lists by "type name", so this leafref
        // matches the name in any address family; family precision is not
        // enforced (legacy-equivalent).
        type leafref {
          path "/frr-filter:lib/frr-filter:prefix-list/frr-filter:name";
          require-instance false;
        }
        description
          "'neighbor X prefix-list NAME in'.";
      }
      leaf prefix-list-out {
        // Inline leafref, kept lax (require-instance false, see header).
        // Not reusing frr-filter's prefix-list-ref - that typedef is
        // require-instance false and shared with other daemons.
        // frr-filter keys prefix-lists by "type name", so this leafref
        // matches the name in any address family; family precision is not
        // enforced (legacy-equivalent).
        type leafref {
          path "/frr-filter:lib/frr-filter:prefix-list/frr-filter:name";
          require-instance false;
        }
        description
          "'neighbor X prefix-list NAME out'.";
      }
      uses neighbor-af-filters-common;
    }
  }

  grouping neighbor-af-filters-evpn {
    description
      "Per-AF 'filters' container for l2vpn-evpn.";

    container filters {
      must "not(distribute-list-in and prefix-list-in)" {
        error-message
          "distribute-list and prefix-list are mutually exclusive
           per direction (in)";
      }
      must "not(distribute-list-out and prefix-list-out)" {
        error-message
          "distribute-list and prefix-list are mutually exclusive
           per direction (out)";
      }
      description
        "Per-direction filtering (bgp_config_write_filter in
         bgpd/bgp_vty.c). Note FRR's 'one slot' rule: distribute-list
         and prefix-list are mutually exclusive per direction (the
         'must' pair).";
      leaf distribute-list-in {
        // Inline leafref, kept lax (require-instance false, see header).
        // Not reusing frr-filter's access-list-ref - that typedef is
        // require-instance false and shared with other daemons.
        // frr-filter keys access-lists by "type name", so this leafref
        // matches the name in any address family; family precision is not
        // enforced (legacy-equivalent).
        type leafref {
          path "/frr-filter:lib/frr-filter:access-list/frr-filter:name";
          require-instance false;
        }
        description
          "'neighbor X distribute-list NAME in'.";
      }
      leaf distribute-list-out {
        // Inline leafref, kept lax (require-instance false, see header).
        // Not reusing frr-filter's access-list-ref - that typedef is
        // require-instance false and shared with other daemons.
        // frr-filter keys access-lists by "type name", so this leafref
        // matches the name in any address family; family precision is not
        // enforced (legacy-equivalent).
        type leafref {
          path "/frr-filter:lib/frr-filter:access-list/frr-filter:name";
          require-instance false;
        }
        description
          "'neighbor X distribute-list NAME out'.";
      }
      leaf prefix-list-in {
        // Inline leafref, kept lax (require-instance false, see header).
        // Not reusing frr-filter's prefix-list-ref - that typedef is
        // require-instance false and shared with other daemons.
        // frr-filter keys prefix-lists by "type name", so this leafref
        // matches the name in any address family; family precision is not
        // enforced (legacy-equivalent).
        type leafref {
          path "/frr-filter:lib/frr-filter:prefix-list/frr-filter:name";
          require-instance false;
        }
        description
          "'neighbor X prefix-list NAME in'.";
      }
      leaf prefix-list-out {
        // Inline leafref, kept lax (require-instance false, see header).
        // Not reusing frr-filter's prefix-list-ref - that typedef is
        // require-instance false and shared with other daemons.
        // frr-filter keys prefix-lists by "type name", so this leafref
        // matches the name in any address family; family precision is not
        // enforced (legacy-equivalent).
        type leafref {
          path "/frr-filter:lib/frr-filter:prefix-list/frr-filter:name";
          require-instance false;
        }
        description
          "'neighbor X prefix-list NAME out'.";
      }
      uses neighbor-af-filters-common;
    }
  }

  /*
   * Instance-level per-address-family building blocks.
   */
  grouping af-route-selection {
    description
      "Per-AF route selection / RIB interaction knobs common to every
       address family we model.";

    container maximum-paths {
      description
        "'maximum-paths ...' (bgp_config_write_maxpaths in
         bgpd/bgp_vty.c). The CLI upper bound is the compile-time
         MULTIPATH_NUM (commonly 64 or 128); modeled as uint16
         without a tighter range on purpose.";
      leaf ebgp {
        type uint16 {
          range "1..max";
        }
        description
          "'maximum-paths N'.";
      }
      leaf ibgp {
        type uint16 {
          range "1..max";
        }
        description
          "'maximum-paths ibgp N [equal-cluster-length]'.";
      }
      leaf ibgp-equal-cluster-length {
        type boolean;
        default "false";
        description
          "Only multipath iBGP routes whose cluster lists are the
           same length.";
      }
    }

    leaf table-map {
      // Inline leafref, kept lax (require-instance false, see header).
      // Not reusing frr-route-map:route-map-ref - that typedef is
      // require-instance false and shared with other daemons.
      type leafref {
        path "/frr-route-map:lib/frr-route-map:route-map/frr-route-map:name";
        require-instance false;
      }
      description
        "'table-map NAME': route-map filtering/modifying what BGP
         downloads to the RIB (bgp_config_write_table_map in
         bgp_route.c).";
    }

    container dampening {
      must "not(reuse-threshold or suppress-threshold or max-suppress-time)
            or (half-life and reuse-threshold and suppress-threshold
                and max-suppress-time)" {
        error-message
          "dampening takes none of the numbers, only half-life, or
           all four";
      }
      description
        "'bgp dampening [(1-45) [(1-20000) (1-50000) (1-255)]]':
         AF-level route-flap dampening (bgp_config_write_damp in
         bgp_damp.c). Same all-or-nothing parameter grouping as the
         per-neighbor variant (the 'must').";
      leaf enabled {
        type boolean;
        default "false";
      }
      leaf half-life {
        type uint8 {
          range "1..45";
        }
        units "minutes";
      }
      leaf reuse-threshold {
        type uint16 {
          range "1..20000";
        }
      }
      leaf suppress-threshold {
        type uint16 {
          range "1..50000";
        }
      }
      leaf max-suppress-time {
        type uint8 {
          range "1..255";
        }
        units "minutes";
      }
    }

    /*
     * The 'distance' container is NOT part of this grouping: its
     * per-prefix override list carries a family-typed prefix, so every
     * AF container pairs 'uses af-route-selection' with the matching
     * 'uses af-distance-<family>' below.
     */
  }

  grouping distance-admin {
    description
      "The 'distance bgp (1-255) (1-255) (1-255)' triple, shared by
       both family variants of the distance container.";

    leaf ebgp {
      type uint8 {
        range "1..255";
      }
      description
        "'distance bgp (1-255) (1-255) (1-255)', first argument.
         All three must be set together -- one CLI line (the
         'must' on the container).";
    }
    leaf ibgp {
      type uint8 {
        range "1..255";
      }
    }
    leaf local {
      type uint8 {
        range "1..255";
      }
    }
  }

  grouping af-distance-ipv4 {
    description
      "Administrative distance for IPv4 address families.";

    container distance {
      must "(ebgp and ibgp and local) or not(ebgp or ibgp or local)" {
        error-message
          "'distance bgp' takes all three distances together";
      }
      description
        "Administrative distance (bgp_config_write_distance in
         bgp_route.c).";
      uses distance-admin;
      list prefix {
        key "prefix";
        description
          "'distance (1-255) A.B.C.D/M [ACCESSLIST_NAME]': distance
           override for routes matching a source prefix.";
        leaf prefix {
          type inet:ipv4-prefix;
        }
        leaf distance {
          type uint8 {
            range "1..255";
          }
          mandatory true;
        }
        leaf access-list {
          // Inline leafref, kept lax (require-instance false, see header).
          // Not reusing frr-filter's access-list-ref - that typedef is
          // require-instance false and shared with other daemons.
          // frr-filter keys access-lists by "type name", so this leafref
          // matches the name in any address family; family precision is not
          // enforced (legacy-equivalent).
          type leafref {
            path "/frr-filter:lib/frr-filter:access-list/frr-filter:name";
            require-instance false;
          }
        }
      }
    }
  }

  grouping af-distance-ipv6 {
    description
      "Administrative distance for IPv6 address families.";

    container distance {
      must "(ebgp and ibgp and local) or not(ebgp or ibgp or local)" {
        error-message
          "'distance bgp' takes all three distances together";
      }
      description
        "Administrative distance (bgp_config_write_distance in
         bgp_route.c).";
      uses distance-admin;
      list prefix {
        key "prefix";
        description
          "'distance (1-255) X:X::X:X/M [ACCESSLIST_NAME]': distance
           override for routes matching a source prefix.";
        leaf prefix {
          type inet:ipv6-prefix;
        }
        leaf distance {
          type uint8 {
            range "1..255";
          }
          mandatory true;
        }
        leaf access-list {
          // Inline leafref, kept lax (require-instance false, see header).
          // Not reusing frr-filter's access-list-ref - that typedef is
          // require-instance false and shared with other daemons.
          // frr-filter keys access-lists by "type name", so this leafref
          // matches the name in any address family; family precision is not
          // enforced (legacy-equivalent).
          type leafref {
            path "/frr-filter:lib/frr-filter:access-list/frr-filter:name";
            require-instance false;
          }
        }
      }
    }
  }

  grouping af-redistribute {
    description
      "'redistribute ...' -- unicast address families only
       (bgp_config_write_redistribute in bgpd/bgp_vty.c returns early
       for every other SAFI).";

    list redistribute {
      key "protocol instance";
      description
        "'redistribute <protocol> [instance] [metric (0-4294967295)]
         [route-map NAME]'. The instance number is only valid for
         ospf/ospf6, table and table-direct ('redistribute
         <ospf|table|table-direct> (1-65535)'); use 0 -- part of the
         key, so it must always be present -- for protocols without
         one.";

      leaf protocol {
        type enumeration {
          enum babel;
          enum connected;
          enum eigrp;
          enum isis;
          enum kernel;
          enum local;
          enum nhrp;
          enum openfabric;
          enum ospf {
            description
              "IPv4 address families only.";
          }
          enum ospf6 {
            description
              "IPv6 address families only.";
          }
          enum rip {
            description
              "IPv4 address families only.";
          }
          enum ripng {
            description
              "IPv6 address families only.";
          }
          enum sharp;
          enum static;
          enum table;
          enum table-direct;
        }
        description
          "Source protocol (FRR's generated FRR_IP[6]_REDIST_STR_BGPD
           token set, minus vnc).
           // The v4/v6-only restrictions are not enforced: this
           // grouping is shared by all AFs, so it would need per-AF
           // enum copies or per-AF 'must' statements at every use
           // site. FRR rejects the wrong ones at load time.";
      }
      leaf instance {
        type uint16 {
          range "0..65535";
        }
        description
          "Protocol instance / table number; 0 = none.";
      }
      leaf metric {
        type uint32;
        description
          "'metric (0-4294967295)'.";
      }
      leaf route-map {
        // Inline leafref, kept lax (require-instance false, see header).
        // Not reusing frr-route-map:route-map-ref - that typedef is
        // require-instance false and shared with other daemons.
        type leafref {
          path "/frr-route-map:lib/frr-route-map:route-map/frr-route-map:name";
          require-instance false;
        }
      }
    }
  }

  grouping af-aggregate-ipv4 {
    list aggregate-address {
      key "prefix";
      description
        "'aggregate-address A.B.C.D/M [as-set] [summary-only]
         [route-map NAME] [origin <egp|igp|incomplete>]
         [matching-MED-only] [suppress-map NAME]'
         (bgp_config_write_network in bgp_route.c).";
      leaf prefix {
        type inet:ipv4-prefix;
      }
      uses aggregate-address-options;
    }
  }

  grouping af-aggregate-ipv6 {
    list aggregate-address {
      key "prefix";
      description
        "'aggregate-address X:X::X:X/M [...]' -- same options as the
         IPv4 form.";
      leaf prefix {
        type inet:ipv6-prefix;
      }
      uses aggregate-address-options;
    }
  }

  grouping aggregate-address-options {
    leaf as-set {
      type boolean;
      default "false";
      description
        "Generate an AS_SET of the contributors' paths.";
    }
    leaf summary-only {
      type boolean;
      default "false";
      description
        "Suppress the more-specific contributors.";
    }
    leaf route-map {
      // Inline leafref, kept lax (require-instance false, see header).
      // Not reusing frr-route-map:route-map-ref - that typedef is
      // require-instance false and shared with other daemons.
      type leafref {
        path "/frr-route-map:lib/frr-route-map:route-map/frr-route-map:name";
        require-instance false;
      }
      description
        "Apply to the aggregate route's attributes.";
    }
    leaf origin {
      type enumeration {
        enum egp;
        enum igp;
        enum incomplete;
      }
    }
    leaf matching-med-only {
      type boolean;
      default "false";
      description
        "'matching-MED-only': only aggregate contributors with equal
         MED.";
    }
    leaf suppress-map {
      // Inline leafref, kept lax (require-instance false, see header).
      // Not reusing frr-route-map:route-map-ref - that typedef is
      // require-instance false and shared with other daemons.
      type leafref {
        path "/frr-route-map:lib/frr-route-map:route-map/frr-route-map:name";
        require-instance false;
      }
      description
        "Suppress only the contributors the route-map matches.";
    }
  }

  grouping af-network-ipv4 {
    list network {
      key "prefix";
      description
        "'network A.B.C.D/M [route-map NAME]
         [label-index (0-1048560)] [backdoor]'
         (bgp_config_write_network in bgp_route.c;
         bgp_network_cmd).";
      leaf prefix {
        type inet:ipv4-prefix;
      }
      uses network-options;
      leaf backdoor {
        type boolean;
        default "false";
        description
          "IPv4 only: install as a backdoor route (worse admin
           distance, not advertised).";
      }
    }
  }

  grouping af-network-ipv6 {
    list network {
      key "prefix";
      description
        "'network X:X::X:X/M [route-map NAME]
         [label-index (0-1048560)]'.";
      leaf prefix {
        type inet:ipv6-prefix;
      }
      uses network-options;
    }
  }

  /*
   * MPLS-VPN static 'network' statements
   * ('network <prefix> rd ASN:NN_OR_IP-ADDRESS:NN <tag|label>
   * (0-1048575) [route-map RMAP_NAME]', vpnv4_network_cmd /
   * vpnv6_network_cmd in bgp_mplsvpn.c; written back by
   * bgp_config_write_network_vpn in bgp_route.c as
   * 'network P rd RD label N [route-map R]' -- 'tag' is an
   * input-side alias for 'label').
   *
   * FRR keys these statics by (rd, prefix): the same prefix may
   * recur under different RDs, so both must be in the YANG key.
   * YANG keys must be leaves, and the RD is structured -- so, same
   * answer as pt:route-target-set: one list per RD encoding with
   * the RD components themselves as key leaves (plus the raw
   * escape-hatch list, whose verbatim RD string is the key).
   * The blocked type-6 MAC encoding is omitted entirely: FRR can't
   * parse it, and unlike pt:route-distinguisher's must-false()
   * member a key leaf can't be blocked without also blocking the
   * list.
   */
  grouping af-network-vpn-ipv4 {
    container network {
      description
        "MPLS-VPN static 'network' statements, IPv4 form
         (vpnv4_network_cmd), grouped by RD encoding -- see the
         comment above the grouping.";
      list as2 {
        key "prefix administrator assigned-number";
        description
          "Entries whose rd is type 0 ('<2-byte-AS>:<NN>').";
        leaf prefix {
          type inet:ipv4-prefix;
        }
        uses vpn-network-rd-as2;
        uses vpn-network-attributes;
      }
      list ipv4 {
        key "prefix administrator assigned-number";
        description
          "Entries whose rd is type 1 ('<A.B.C.D>:<NN>').";
        leaf prefix {
          type inet:ipv4-prefix;
        }
        uses vpn-network-rd-ipv4;
        uses vpn-network-attributes;
      }
      list as4 {
        key "prefix administrator assigned-number";
        description
          "Entries whose rd is type 2 ('<4-byte-AS>:<NN>',
           RFC 5668-style).";
        leaf prefix {
          type inet:ipv4-prefix;
        }
        uses vpn-network-rd-as4;
        uses vpn-network-attributes;
      }
      list raw {
        key "prefix rd";
        description
          "Fallback: entries whose rd text is emitted verbatim, for
           values outside every structured encoding.";
        leaf prefix {
          type inet:ipv4-prefix;
        }
        leaf rd {
          type string;
          description
            "The rd text, verbatim.";
        }
        uses vpn-network-attributes;
      }
    }
  }

  grouping af-network-vpn-ipv6 {
    container network {
      description
        "MPLS-VPN static 'network' statements, IPv6 form
         (vpnv6_network_cmd), grouped by RD encoding -- see the
         comment above af-network-vpn-ipv4.";
      list as2 {
        key "prefix administrator assigned-number";
        description
          "Entries whose rd is type 0 ('<2-byte-AS>:<NN>').";
        leaf prefix {
          type inet:ipv6-prefix;
        }
        uses vpn-network-rd-as2;
        uses vpn-network-attributes;
      }
      list ipv4 {
        key "prefix administrator assigned-number";
        description
          "Entries whose rd is type 1 ('<A.B.C.D>:<NN>').";
        leaf prefix {
          type inet:ipv6-prefix;
        }
        uses vpn-network-rd-ipv4;
        uses vpn-network-attributes;
      }
      list as4 {
        key "prefix administrator assigned-number";
        description
          "Entries whose rd is type 2 ('<4-byte-AS>:<NN>',
           RFC 5668-style).";
        leaf prefix {
          type inet:ipv6-prefix;
        }
        uses vpn-network-rd-as4;
        uses vpn-network-attributes;
      }
      list raw {
        key "prefix rd";
        description
          "Fallback: entries whose rd text is emitted verbatim, for
           values outside every structured encoding.";
        leaf prefix {
          type inet:ipv6-prefix;
        }
        leaf rd {
          type string;
          description
            "The rd text, verbatim.";
        }
        uses vpn-network-attributes;
      }
    }
  }

  grouping vpn-network-rd-as2 {
    leaf administrator {
      type uint16;
      description
        "RD administrator subfield: 2-byte AS number.";
    }
    leaf assigned-number {
      type uint32;
      description
        "RD 4-byte assigned number subfield.";
    }
  }

  grouping vpn-network-rd-ipv4 {
    leaf administrator {
      type inet:ipv4-address-no-zone;
      description
        "RD administrator subfield: IPv4 address.";
    }
    leaf assigned-number {
      type uint16;
      description
        "RD 2-byte assigned number subfield.";
    }
  }

  grouping vpn-network-rd-as4 {
    leaf administrator {
      type uint32;
      description
        "RD administrator subfield: 4-byte AS number.";
    }
    leaf assigned-number {
      type uint16;
      description
        "RD 2-byte assigned number subfield.";
    }
  }

  grouping vpn-network-attributes {
    leaf label {
      type uint32 {
        range "0..1048575";
      }
      mandatory true;
      description
        "'label (0-1048575)': MPLS label carried in the VPN NLRI.";
    }
    leaf route-map {
      // Inline leafref, kept lax (require-instance false, see header).
      // Not reusing frr-route-map:route-map-ref - that typedef is
      // require-instance false and shared with other daemons.
      type leafref {
        path "/frr-route-map:lib/frr-route-map:route-map/frr-route-map:name";
        require-instance false;
      }
    }
  }

  grouping network-options {
    leaf route-map {
      // Inline leafref, kept lax (require-instance false, see header).
      // Not reusing frr-route-map:route-map-ref - that typedef is
      // require-instance false and shared with other daemons.
      type leafref {
        path "/frr-route-map:lib/frr-route-map:route-map/frr-route-map:name";
        require-instance false;
      }
    }
    leaf label-index {
      type uint32 {
        range "0..1048560";
      }
      description
        "SR label index (labeled-unicast).";
    }
  }

  grouping af-retain-route-target {
    leaf retain-route-target-all {
      type boolean;
      default "true";
      description
        "'bgp retain route-target all' / 'no bgp retain
         route-target all': keep all received VPN routes
         regardless of route-target import filtering. Default on
         -- disabling it keeps only VPN routes whose route-targets
         match a local VRF import; only the 'no' form is written
         to the configuration.";
    }
  }

  grouping af-srv6-sid-export {
    description
      "'[no] sid export <(1-1048575)|auto|explicit X:X::X:X>
       [behavior dt46] [route-map RMAP]' (sid_export_cmd, M8.5
       B-srv6-unicast): SRv6 SID attached to unicast routes of the
       default VRF. Default-instance-only and mutually exclusive
       with both 'sid vpn export' forms (VALIDATE-checked). SID
       allocation is asynchronous; convergence in the container
       apply_finish.";

    container srv6-sid-export {
      presence
        "'sid export ...' is configured for this AF.";

      choice sid {
        case index {
          leaf index {
            type uint32 {
              range "1..1048575";
            }
            description
              "SID allocation index-mode.";
          }
        }
        case auto {
          leaf auto {
            type boolean;
            default "false";
            description
              "SID allocation auto-mode.";
          }
        }
        case explicit {
          leaf explicit {
            type inet:ipv6-address-no-zone;
            description
              "Explicitly assigned SID value.";
          }
        }
      }

      leaf behavior-dt46 {
        type boolean;
        default "false";
        description
          "'behavior dt46': allocate a DT46 SID shared by both
           unicast AFs; requires both AFs' sid mode/index/value to
           agree (candidate-side VALIDATE).";
      }

      leaf route-map {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "'route-map RMAP': filter which unicast routes get the
           SID.";
      }
    }
  }

  grouping af-vpn-leaking {
    description
      "Route leaking between this unicast AF and the VPN table /
       other VRFs: the simple 'import|export vpn' / 'import vrf'
       knobs plus the detailed vpn-policy block written by
       bgp_vpn_policy_config_write_afi in bgp_vty.c.";

    leaf export-vpn {
      type boolean;
      default "false";
      description
        "'export vpn'.";
    }
    leaf import-vpn {
      type boolean;
      default "false";
      description
        "'import vpn'.";
    }
    leaf-list import-vrf {
      type string;
      description
        "'import vrf NAME' lines.
         // Deliberately not a leafref to /instance/vrf: FRR
         // auto-creates the target instance if it doesn't exist.";
    }
    leaf import-vrf-route-map {
      // Inline leafref, kept lax (require-instance false, see header).
      // Not reusing frr-route-map:route-map-ref - that typedef is
      // require-instance false and shared with other daemons.
      type leafref {
        path "/frr-route-map:lib/frr-route-map:route-map/frr-route-map:name";
        require-instance false;
      }
      description
        "'import vrf route-map NAME'
         (af_import_vrf_route_map_cmd): filter applied to
         vrf-to-vrf imports. In FRR this shares the import
         route-map slot with 'route-map vpn import' (which the
         must below therefore forbids alongside it); unlike the
         vpn block it stays effective while 'import vrf' is
         active -- setting it even flags the AF for vrf-to-vrf
         import on its own.";
    }
    container vpn {
      description
        "Detailed MPLS L3VPN leaking policy for this AF: the
         '... vpn import|export ...' lines written by
         bgp_vpn_policy_config_write_afi (bgp_vty.c). FRR's
         config-write skips this whole block (except the import
         route-map) while vrf-to-vrf leaking ('import vrf') is
         active on the AF -- the vpn policy machinery is
         vrf<->vpn-table leaking, not vrf<->vrf.
         // 'sid vpn export' (SRv6) and 'rt|rt6 redirect import'
         // (flowspec redirect) are excluded per module scope --
         // see the module description.";

      leaf route-map-import {
        // Inline leafref, kept lax (require-instance false, see header).
        // Not reusing frr-route-map:route-map-ref - that typedef is
        // require-instance false and shared with other daemons.
        type leafref {
          path "/frr-route-map:lib/frr-route-map:route-map/frr-route-map:name";
          require-instance false;
        }
        must "not(../../import-vrf-route-map)" {
          error-message
            "route-map vpn import and import vrf route-map occupy
             the same import-route-map slot in FRR (rmap_name
             [BGP_VPN_POLICY_DIR_FROMVPN]) -- configure only one";
        }
        description
          "'route-map vpn import NAME'
           (af_route_map_vpn_imexport_cmd): filter applied to
           routes leaked from the VPN table into this AF.";
      }
      leaf route-map-export {
        // Inline leafref, kept lax (require-instance false, see header).
        // Not reusing frr-route-map:route-map-ref - that typedef is
        // require-instance false and shared with other daemons.
        type leafref {
          path "/frr-route-map:lib/frr-route-map:route-map/frr-route-map:name";
          require-instance false;
        }
        description
          "'route-map vpn export NAME': filter applied to routes
           leaked from this AF to the VPN table.";
      }
      container label-export {
        description
          "MPLS label attached to routes leaked to the VPN table.";
        choice label {
          description
            "'label vpn export <(0-1048575)|auto>'
             (af_label_vpn_export_cmd): a fixed label value or
             kernel-allocated ('auto') -- one storage slot in FRR,
             hence a choice.";
          case value {
            leaf value {
              type uint32 {
                range "0..1048575";
              }
              description
                "Fixed MPLS label value.";
            }
          }
          case auto {
            leaf auto {
              type boolean;
              default "false";
              description
                "'label vpn export auto': allocate the label
                 dynamically (from zebra's label manager).";
            }
          }
        }
        leaf allocation-mode {
          type enumeration {
            enum per-vrf {
              description
                "One label for the whole VRF (FRR's default).";
            }
            enum per-nexthop {
              description
                "One label per nexthop of the leaked routes.";
            }
          }
          description
            "'label vpn export allocation-mode
             <per-vrf|per-nexthop>'
             (af_label_vpn_export_allocation_mode_cmd). per-vrf is
             FRR's default; its config-write emits only the
             per-nexthop form, but we render an explicitly
             configured per-vrf too -- loadable, resets to the
             default.";
        }
      }
      container sid-export {
        presence
          "'sid vpn export ...' is configured for this AF (M8.5
           B-srv6-peraf-vpn). Same shape as the instance-level
           sid-vpn-export; mutually exclusive with it and with the
           unicast 'sid export' (VALIDATE-checked). Converged in the
           enclosing vpn container's apply_finish next to
           label-export.";
        description
          "'[no] sid vpn export <(1-4294967295)|auto|explicit
           X:X::X:X>' (af_sid_vpn_export_cmd): SRv6 SID for routes
           leaked from this AF to the VPN table.";

        choice sid {
          case index {
            leaf index {
              type uint32 {
                range "1..4294967295";
              }
              description
                "SID allocation index-mode.";
            }
          }
          case auto {
            leaf auto {
              type boolean;
              default "false";
              description
                "SID allocation auto-mode.";
            }
          }
          case explicit {
            leaf explicit {
              type inet:ipv6-address-no-zone;
              description
                "Explicitly assigned SID value.";
            }
          }
        }
      }
      container flowspec-redirect-import {
        presence
          "'rt|rt6 redirect import ...' is configured (M8.5
           B-fs-extras): flowspec redirect-to-VRF route-target
           import list (vpn_policy import_redirect_rtlist).";
        description
          "'[no] <rt|route-target|rt6|route-target6> redirect import
           RTLIST...' (af_routetarget_import_cmd). Full-replace
           semantics like legacy; converged with the other vpn
           leaves in the vpn container's apply_finish.";

        leaf ipv6-format {
          type boolean;
          default "false";
          description
            "The rt6/route-target6 keyword form (IPv6-format route
             targets; only valid under ipv6-unicast).";
        }

        leaf-list route-targets {
          type string;
          description
            "Route-target tokens as typed
             (A.B.C.D:MN|EF:OPQR|GHJK:MN|IPV6:MN).";
        }
      }
      container rd-export {
        description
          "'rd vpn export <ASN:NN|A.B.C.D:NN>'
           (af_rd_vpn_export_cmd): route distinguisher stamped on
           routes leaked to the VPN table.";
        presence "An export RD is configured for VPN route
                  leaking.";
        uses pt:route-distinguisher;
      }
      leaf nexthop-export {
        type union {
          type inet:ipv4-address-no-zone;
          type inet:ipv6-address-no-zone;
        }
        description
          "'nexthop vpn export <A.B.C.D|X:X::X:X>'
           (af_nexthop_vpn_export_cmd): nexthop stamped on routes
           leaked to the VPN table (the DEFPY accepts either
           family under either AF). FRR only persists the
           with-address form, so the leaf is the address.";
      }
      container rt-import {
        description
          "'rt vpn import RTLIST' (af_rt_vpn_imexport_cmd): route
           targets a VPN route must carry (match any) to be leaked
           into this AF.";
        uses pt:route-target-set;
      }
      container rt-export {
        description
          "'rt vpn export RTLIST': route targets attached to
           routes leaked from this AF to the VPN table. FRR's
           config-write collapses equal import+export sets into
           one 'rt vpn both' line; we always emit the two
           per-direction lines -- FRR parses them to the same
           state.";
        uses pt:route-target-set;
      }
    }
  }

  container process {
    description
      "Process-wide settings written before any 'router bgp' block
       ('bgp ...' lines at config top level; the bm-> globals at
       the start of bgp_config_write in bgpd/bgp_vty.c).";

    leaf route-map-delay-timer {
      type uint16 {
        range "0..600";
      }
      units "seconds";
      description
        "'bgp route-map delay-timer (0-600)'.";
    }

    leaf agentx {
      type boolean;
      default "false";
      description
        "'agentx': connect to the SNMP master agent as an AgentX
         subagent. Tier A default-off: the bare 'agentx' line
         renders iff true. Once enabled, AgentX support cannot be
         disabled again for the lifetime of the process.";
    }

    container snmp-traps {
      description
        "'bgp snmp traps ...' (M8.5 B-snmp): trap-family toggles on
         bm->options. Core bgpd state; the SNMP module only consumes
         the flags, so they are settable regardless of whether the
         bgpd_snmp module is loaded (the compiled-in defaults moved
         from the module init to bgp_master_init for exactly that
         parity).";

      leaf rfc4273 {
        type boolean;
        default "true";
        description
          "'bgp snmp traps rfc4273'. Tier A default-on: the legacy
           'no ...' line renders iff false.";
      }

      leaf rfc4382 {
        type boolean;
        default "true";
        description
          "'bgp snmp traps rfc4382'. Tier A default-on.";
      }

      leaf bgp4-mibv2 {
        type boolean;
        default "false";
        description
          "'bgp snmp traps bgp4-mibv2'. Tier A default-off,
           positive-only emission.";
      }
    }
    container update-delay {
      description
        "'bgp update-delay (0-3600) [(1-3600)]' (process-wide;
         mutually exclusive with the per-instance form).";
      leaf delay {
        type uint16 {
          range "0..3600";
        }
        units "seconds";
      }
      leaf establish-wait {
        type uint16 {
          range "1..3600";
        }
        units "seconds";
      }
    }
    leaf advertisement-delay {
      type uint16 {
        range "1..3600";
      }
      units "seconds";
      description
        "'bgp advertisement-delay (1-3600)'.";
    }
    container suppress-fib-pending {
      description
        "'bgp suppress-fib-pending [(0-10000)]': wait for FIB
         install before advertising, globally.";
      leaf enabled {
        type boolean;
        default "false";
      }
      leaf advertisement-delay {
        type uint16 {
          range "0..10000";
        }
        units "milliseconds";
        default "1000";
        description
          "Static default-on scalar, no inheritance (YANG default
           1000, BGP_DEFAULT_SUPPRESS_FIB_ADV_DELAY in bgpd.h);
           bgp_config_write() in bgpd/bgp_vty.c prints the value
           only when it differs from this default.";
      }
    }
    container graceful-restart {
      description
        "Process-wide graceful-restart settings; each is mutually
         exclusive with its per-instance twin.";
      leaf mode {
        type enumeration {
          enum restarter {
            description
              "'bgp graceful-restart'.";
          }
          enum disable {
            description
              "'bgp graceful-restart-disable'.";
          }
        }
        description
          "Unset means FRR's default (helper mode).";
      }
      leaf preserve-fw-state {
        type boolean;
        default "false";
        description
          "'bgp graceful-restart preserve-fw-state'.";
      }
      leaf restart-time {
        type uint16 {
          range "0..4095";
        }
        units "seconds";
        description
          "'bgp graceful-restart restart-time (0-4095)'.";
      }
      leaf stalepath-time {
        type uint16 {
          range "1..4095";
        }
        units "seconds";
        description
          "'bgp graceful-restart stalepath-time (1-4095)'.";
      }
      leaf select-defer-time {
        type uint16 {
          range "0..3600";
        }
        units "seconds";
        description
          "'bgp graceful-restart select-defer-time (0-3600)'.";
      }
      leaf rib-stale-time {
        type uint16 {
          range "1..3600";
        }
        units "seconds";
        description
          "'bgp graceful-restart rib-stale-time (1-3600)'.";
      }
    }
    leaf graceful-shutdown {
      type boolean;
      default "false";
      description
        "'bgp graceful-shutdown' (process-wide; mutually exclusive
         with the per-instance form).";
    }
    leaf no-rib {
      type boolean;
      default "false";
      description
        "'bgp no-rib': do not install routes into zebra.";
    }
    leaf send-extra-data-zebra {
      type boolean;
      default "false";
      description
        "'bgp send-extra-data zebra'.";
    }
    leaf ipv6-auto-ra {
      type boolean;
      default "true";
      description
        "'bgp ipv6-auto-ra' / 'no bgp ipv6-auto-ra' (process scope),
         emitted by bgp_config_write() in bgpd/bgp_vty.c. Static
         default-on boolean, chain root for
         /proteus-bgp:instance/ipv6-auto-ra's per-VRF override:
         libyang persistence does the work, an explicit false is a
         real node and gets written, the implicit true default is
         not; the legacy 'no ...' line renders iff the value is
         false.";
    }
    leaf session-dscp {
      type uint8 {
        range "0..63";
      }
      description
        "'bgp session-dscp (0-63)': DSCP for outgoing BGP TCP
         packets.";
    }
    leaf input-queue-limit {
      type uint32 {
        range "1..4294967295";
      }
      description
        "'bgp input-queue-limit (1-4294967295)'.";
    }
    leaf output-queue-limit {
      type uint32 {
        range "1..4294967295";
      }
      description
        "'bgp output-queue-limit (1-4294967295)'.";
    }
  }

  list instance {
    key "vrf";
    must "autonomous-system/plain or autonomous-system/asdot/high" {
      error-message
        "autonomous-system is mandatory: every 'router bgp' block
         carries its ASN (an all-empty container counts as
         unconfigured, so the requirement lives here on the
         parent, not as a mandatory choice).";
    }
    description
      "One 'router bgp ASN [<view|vrf> NAME]' block. FRR allows
       exactly one BGP instance per VRF, so the VRF name is the
       key.";

    leaf vrf {
      type string {
        length "1..36";
      }
      description
        "VRF this instance runs in. 'default' means the default
         VRF; it is rendered as plain 'router bgp ASN' with no
         vrf clause.";
    }

    leaf instance-type {
      type enumeration {
        enum vrf {
          description
            "'router bgp ASN vrf NAME' (or the default instance).";
        }
        enum view {
          description
            "'router bgp ASN view NAME': a view shares the default
             VRF's kernel table.";
        }
      }
      default "vrf";
      description
        "Whether a named instance is a VRF or a view.";
    }

    container autonomous-system {
      uses pt:as-number-notation;
      description
        "Local autonomous system number: the ASN token of
         'router bgp ASN' (router_bgp_cmd), in plain decimal or
         structured asdot notation -- rendered exactly as
         configured. FRR parses either notation independent of the
         as-notation leaf, which only selects the display notation
         of later show output. Required: the must on the instance
         list.";
    }

    leaf as-notation {
      type enumeration {
        enum plain {
          description
            "Always plain 32-bit decimal.";
        }
        enum dot {
          description
            "asdot: '<high>.<low>' for ASNs above 65535, plain
             decimal below (RFC 5396 asdot).";
        }
        enum dot+ {
          description
            "asdot+: '<high>.<low>' for every ASN, including
             '0.<low>' for 2-byte ASNs.";
        }
      }
      description
        "'router bgp ASN ... as-notation <dot|dot+|plain>'
         (router_bgp_cmd; written as a header-line suffix after the
         view/vrf clause by bgp_config_write, asn_mode2str in
         lib/asn.c). Display-only: it selects the notation FRR uses
         for ASNs in show output and does not constrain how the
         autonomous-system value itself is written here. Only
         emitted when explicitly configured (BGP_CONFIG_ASNOTATION),
         matching the unset-renders-nothing convention.";
    }

    leaf router-id {
      type yang:dotted-quad;
      description
        "'bgp router-id A.B.C.D' (bgp_router_id_cmd). A 32-bit
         identifier in dotted notation, not an address (RFC 6991
         dotted-quad).";
    }

    leaf cluster-id {
      type union {
        type yang:dotted-quad;
        type uint32 {
          range "1..4294967295";
        }
      }
      description
        "'bgp cluster-id <A.B.C.D|(1-4294967295)>': a 32-bit
         identifier, in dotted notation or plain decimal (RFC 6991
         dotted-quad, not an address).";
    }

    leaf fast-external-failover {
      type boolean;
      default "true";
      description
        "'bgp fast-external-failover' / 'no bgp
         fast-external-failover', emitted by bgp_config_write() in
         bgpd/bgp_vty.c. Static default-on boolean, no inheritance:
         libyang persistence does the work, an explicit false is a
         real node and gets written, the implicit true default is
         not; the legacy 'no ...' line renders iff the value is
         false.";
    }

    leaf ipv6-auto-ra {
      type boolean;
      description
        "'bgp ipv6-auto-ra <enabled|disabled>' (per-VRF override;
         also 'no bgp ipv6-auto-ra <enabled|disabled>' to unset),
         emitted inside the 'router bgp' block by bgp_config_write()
         in bgpd/bgp_vty.c. Tri-state: no YANG default (a default and
         inheritance are mutually exclusive on a leaf -- the default
         lives at the chain root, /proteus-bgp:process/ipv6-auto-ra,
         which carries a static default of true); unset means inherit
         the process leaf's effective value for this instance; an
         explicit value, once set, overrides the process-wide setting
         for this VRF only and is always rendered explicitly.
         Deprecated bare 'bgp ipv6-auto-ra' / 'no bgp ipv6-auto-ra'
         aliases keep loading configs saved before this leaf grew the
         enabled|disabled grammar (bare means true, bare 'no'
         persists an explicit false).";
    }

    container suppress-fib-pending {
      description
        "'bgp suppress-fib-pending [(0-10000)]', per-instance
         form.";
      leaf enabled {
        type boolean;
        default "false";
      }
      leaf advertisement-delay {
        type uint16 {
          range "0..10000";
        }
        units "milliseconds";
        default "1000";
        description
          "Static default-on scalar, no inheritance (YANG default
           1000, BGP_DEFAULT_SUPPRESS_FIB_ADV_DELAY in bgpd.h);
           bgp_config_write() in bgpd/bgp_vty.c prints the value
           only when it differs from this default.";
      }
    }

    leaf log-neighbor-changes {
      type boolean;
      description
        "'bgp log-neighbor-changes <enabled|disabled>' (also 'no bgp
         log-neighbor-changes <enabled|disabled>' to unset), emitted
         by bgp_config_write() in bgpd/bgp_vty.c. Tri-state: no YANG
         default, unset means the compile-profile default (on for
         the datacenter profile, off for traditional); an explicit
         value, once set, is always rendered explicitly. Deprecated
         bare 'bgp log-neighbor-changes' / 'no bgp
         log-neighbor-changes' aliases keep loading configs saved
         before this leaf grew the enabled|disabled grammar (bare
         means true, bare 'no' persists an explicit false).";
    }

    leaf always-compare-med {
      type boolean;
      default "false";
      description
        "'bgp always-compare-med'.";
    }

    leaf ebgp-requires-policy {
      type boolean;
      description
        "'[no] bgp ebgp-requires-policy' (RFC 8212). Three-valued:
         unset means the compile-profile default (on for
         traditional, off for datacenter). NOTE: when this is in
         effect, eBGP sessions exchange no routes without an
         explicit per-peer policy.";
    }

    leaf enforce-first-as {
      type boolean;
      description
        "'[no] bgp enforce-first-as' (default on).";
    }

    leaf labeled-unicast-explicit-null {
      type enumeration {
        enum ipv4 {
          description
            "'bgp labeled-unicast ipv4-explicit-null'.";
        }
        enum ipv6 {
          description
            "'bgp labeled-unicast ipv6-explicit-null'.";
        }
        enum both {
          description
            "'bgp labeled-unicast explicit-null'.";
        }
      }
      description
        "Advertise explicit-null instead of implicit-null labels
         for labeled-unicast.";
    }

    leaf reject-as-sets {
      type boolean;
      default "true";
      description
        "'bgp reject-as-sets' / 'no bgp reject-as-sets' (RFC 9774),
         emitted by bgp_config_write() in bgpd/bgp_vty.c. Static
         default-on boolean, no inheritance: libyang persistence does
         the work, an explicit false is a real node and gets written,
         the implicit true default is not; the legacy 'no ...' line
         renders iff the value is false.";
    }

    leaf suppress-duplicates {
      type boolean;
      description
        "'[no] bgp suppress-duplicates' (default on).";
    }

    leaf hard-administrative-reset {
      type boolean;
      description
        "'[no] bgp hard-administrative-reset' (RFC 8538 handling of
         CEASE/Administrative Reset; default on).";
    }

    container segment-routing-srv6 {
      presence
        "The 'segment-routing srv6' block is configured. Presence so
         'no segment-routing srv6' is one whole-container DESTROY
         running the composite legacy unset (locator teardown, encap
         reset, srv6-only back to default). Entering the node alone
         does not create it; the first child leaf does (matching
         legacy, where a bare empty block was never emitted and so
         never survived a restart).";
      description
        "'segment-routing srv6' ... 'exit' block (BGP_SRV6_NODE,
         M8.5 B-srv6-block).";

      leaf locator {
        type string;
        description
          "'locator NAME': SRv6 locator to allocate SIDs from,
           fetched asynchronously from zebra's SRv6 manager. Plain
           string, not a leafref into zebra's locator list (house
           rule: forward references allowed, cross-daemon state).
           Changing it while set is rejected (legacy 'srv6 locator
           is already configured'); delete first.";
      }

      leaf encap-behavior {
        type enumeration {
          enum H_Encaps;
          enum H_Encaps_Red;
        }
        default "H_Encaps";
        description
          "'encap-behavior <H_Encaps|H_Encaps_Red>'. Enum names
           mirror the CLI tokens verbatim for token-driven xpaths.
           Legacy wart preserved: the setter operates on the default
           instance regardless of which instance's block it appears
           in (bgp_get_default() in the legacy handler).";
      }

      leaf srv6-only {
        type boolean;
        default "true";
        description
          "'[no] srv6-only': prefer SRv6 over MPLS for VPN routes.
           Tier A default-on: the 'no srv6-only' line renders iff
           false. Deliberate divergence from legacy's 'no
           segment-routing srv6' handler, which forced this false
           (leaving a stray 'no srv6-only' emission after the block
           was removed): container destroy restores the default.";
      }
    }

    container sid-vpn-export {
      presence
        "'sid vpn per-vrf export ...' is configured (one SRv6 SID for
         both address families' VPN leaking). Presence + choice,
         the label-export house shape; 'no sid vpn per-vrf export'
         destroys the container.";
      description
        "'[no] sid vpn per-vrf export
         <(1-4294967295)|auto|explicit X:X::X:X>' (M8.5
         B-srv6-pervrf). Mutually exclusive with the per-AF
         'sid vpn export' and unicast 'sid export' forms; mode
         changes (index/auto/explicit) require negating first,
         both enforced at VALIDATE against the runtime (the sibling
         forms convert later in the M8.5 train). SID allocation is
         asynchronous via zebra's SRv6 manager; runtime convergence
         happens once per commit in the container apply_finish.";

      choice sid {
        case index {
          leaf index {
            type uint32 {
              range "1..4294967295";
            }
            description
              "SID allocation index-mode.";
          }
        }
        case auto {
          leaf auto {
            type boolean;
            default "false";
            description
              "SID allocation auto-mode.";
          }
        }
        case explicit {
          leaf explicit {
            type inet:ipv6-address-no-zone;
            description
              "Explicitly assigned SID value.";
          }
        }
      }
    }

    container default {
      description
        "The 'bgp default ...' family of per-instance defaults
         (they seed new neighbors / address families).";

      leaf ipv4-unicast {
        type boolean;
        default "true";
        description
          "'bgp default ipv4-unicast' / 'no bgp default
           ipv4-unicast': implicitly activate new neighbors for
           ipv4-unicast, emitted by bgp_config_write() in
           bgpd/bgp_vty.c. Static default-on boolean, no inheritance
           (the only default/<afi-safi> leaf that is on by default):
           libyang persistence does the work, an explicit false is a
           real node and gets written, the implicit true default is
           not; the legacy 'no ...' line renders iff the value is
           false.";
      }
      leaf ipv4-multicast {
        type boolean;
        default "false";
        description
          "'bgp default ipv4-multicast'.";
      }
      leaf ipv4-flowspec {
        type boolean;
        default "false";
        description
          "'bgp default ipv4-flowspec': implicitly activate new
           neighbors for ipv4-flowspec, emitted by
           bgp_config_write()'s FOREACH_AFI_SAFI loop in
           bgpd/bgp_vty.c (bgp_default_afi_safi_cmd handles the
           setter). Positive-only, like its ipv4-multicast sibling:
           FRR default false.";
      }
      leaf ipv4-labeled-unicast {
        type boolean;
        default "false";
        description
          "'bgp default ipv4-labeled-unicast'.";
      }
      leaf ipv4-vpn {
        type boolean;
        default "false";
        description
          "'bgp default ipv4-vpn'.";
      }
      leaf ipv6-unicast {
        type boolean;
        default "false";
        description
          "'bgp default ipv6-unicast'.";
      }
      leaf ipv6-multicast {
        type boolean;
        default "false";
        description
          "'bgp default ipv6-multicast'.";
      }
      leaf ipv6-labeled-unicast {
        type boolean;
        default "false";
        description
          "'bgp default ipv6-labeled-unicast'.";
      }
      leaf ipv6-vpn {
        type boolean;
        default "false";
        description
          "'bgp default ipv6-vpn'.";
      }
      leaf ipv6-flowspec {
        type boolean;
        default "false";
        description
          "'bgp default ipv6-flowspec': implicitly activate new
           neighbors for ipv6-flowspec, emitted by
           bgp_config_write()'s FOREACH_AFI_SAFI loop in
           bgpd/bgp_vty.c (bgp_default_afi_safi_cmd handles the
           setter). Positive-only, like its ipv4-multicast sibling:
           FRR default false.";
      }
      leaf l2vpn-evpn {
        type boolean;
        default "false";
        description
          "'bgp default l2vpn-evpn'.";
      }

      leaf local-preference {
        type uint32;
        default "100";
        description
          "'bgp default local-preference (0-4294967295)'. Static
           default-on scalar, no inheritance: the legacy 'no bgp
           default local-preference' line deletes back to this
           default, matching bgpd.c's bgp_default_local_preference_unset()
           (FRR default 100).";
      }
      leaf show-hostname {
        type boolean;
        description
          "'[no] bgp default show-hostname' (profile-dependent
           default).";
      }
      leaf show-nexthop-hostname {
        type boolean;
        description
          "'[no] bgp default show-nexthop-hostname'.";
      }
      leaf software-version-capability {
        type boolean;
        description
          "'[no] bgp default software-version-capability'.";
      }
      leaf software-version-capability-latest-encoding {
        type boolean;
        description
          "'[no] bgp default software-version-capability
           latest-encoding'.";
      }
      leaf link-local-capability {
        type boolean;
        description
          "'[no] bgp default link-local-capability'.";
      }
      leaf dynamic-capability {
        type boolean;
        description
          "'[no] bgp default dynamic-capability'.";
      }
      leaf subgroup-pkt-queue-max {
        type uint8 {
          range "20..100";
        }
        default "40";
        description
          "'bgp default subgroup-pkt-queue-max (20-100)'. Static
           default-on scalar, no inheritance: the legacy 'no bgp
           default subgroup-pkt-queue-max' line deletes back to this
           default (BGP_DEFAULT_SUBGROUP_PKT_QUEUE_MAX).";
      }
      leaf shutdown {
        type boolean;
        default "false";
        description
          "'bgp default shutdown': new neighbors start
           administratively down (bgp->autoshutdown, seeded into
           each peer at creation). Converted in M8 batch B2, after
           B1 moved the peer/peer-group creation lines to mgmtd's
           emission: the historical placement race (the legacy line
           was written after all neighbor lines so a daemon-restart
           replay would not shut existing peers, FRR issue #2286)
           evaporated because the leaf is future-peers-only - it
           never touches peers that already exist, so its position
           relative to the neighbor lines no longer matters.";
      }
    }

    leaf client-to-client-reflection {
      type boolean;
      default "true";
      description
        "'bgp client-to-client reflection' / 'no bgp
         client-to-client reflection', emitted by bgp_config_write()
         in bgpd/bgp_vty.c. Static default-on boolean, no
         inheritance: libyang persistence does the work, an explicit
         false is a real node and gets written, the implicit true
         default is not; the legacy 'no ...' line renders iff the
         value is false.";
    }

    leaf ebgp-connected-route-check {
      type boolean;
      default "true";
      description
        "'bgp ebgp-connected-route-check <enabled|disabled>': when
         enabled, nexthop connectivity is verified on single-hop EBGP
         sessions; when disabled, that verification is skipped so
         sessions reachable via a non-directly-connected address stay
         up (default enabled).";
    }

    container confederation {
      description
        "'bgp confederation identifier ASN' and
         'bgp confederation peers ASN...'. ASNs follow the
         structured plain/asdot convention; the peers set keeps
         one collection per notation like the route-target-set
         grouping (plain values first, then asdot, on the one
         'peers' line).";
      container identifier {
        uses pt:as-number-notation;
        description
          "'bgp confederation identifier ASN'.";
      }
      container peers {
        description
          "'bgp confederation peers ASN...': the member ASNs.";
        leaf-list plain {
          type pt:as-number;
          description
            "Members given in plain decimal.";
        }
        list asdot {
          key "high low";
          description
            "Members given in asdot notation, rendered
             '<high>.<low>' (the halves are the keys, so
             duplicates are structurally impossible).";
          leaf high {
            type uint16;
            description
              "Upper 16 bits of the ASN.";
          }
          leaf low {
            type uint16;
            description
              "Lower 16 bits of the ASN.";
          }
          must "high != 0 or low != 0" {
            error-message
              "'0.0' is ASN 0, reserved (RFC 7607) and rejected
               by FRR.";
          }
        }
      }
    }

    leaf deterministic-med {
      type boolean;
      description
        "'[no] bgp deterministic-med' (profile-dependent
         default).";
    }

    container update-delay {
      description
        "'update-delay (0-3600) [(1-3600)]', per-instance form
         (mutually exclusive with the process-wide one).";
      leaf delay {
        type uint16 {
          range "0..3600";
        }
        units "seconds";
      }
      leaf establish-wait {
        type uint16 {
          range "1..3600";
        }
        units "seconds";
      }
    }

    leaf advertisement-delay {
      type uint16 {
        range "1..3600";
      }
      units "seconds";
      description
        "'advertisement-delay (1-3600)', per-instance form.";
    }

    container max-med {
      description
        "Advertise MAX_MED to steer traffic away.";
      container on-startup {
        description
          "'bgp max-med on-startup (5-86400) [(0-4294967295)]'.";
        leaf period {
          type uint32 {
            range "5..86400";
          }
          units "seconds";
        }
        leaf med {
          type uint32;
          description
            "MED value; unset means FRR's default
             (4294967294).";
        }
      }
      container administrative {
        description
          "'bgp max-med administrative [(0-4294967295)]'.";
        leaf enabled {
          type boolean;
          default "false";
        }
        leaf med {
          type uint32;
        }
      }
    }

    leaf write-quanta {
      type uint8 {
        range "1..64";
      }
      description
        "'write-quanta (1-64)': packets per write i/o cycle.";
    }
    leaf read-quanta {
      type uint8 {
        range "1..10";
      }
      description
        "'read-quanta (1-10)'.";
    }
    leaf coalesce-time {
      type uint32;
      units "milliseconds";
      description
        "'coalesce-time (0-4294967295)': subgroup coalesce timer.";
    }

    leaf graceful-shutdown {
      type boolean;
      default "false";
      description
        "'bgp graceful-shutdown', per-instance form (mutually
         exclusive with the process-wide one).";
    }

    leaf long-lived-graceful-restart-stale-time {
      type uint32 {
        range "1..16777215";
      }
      units "seconds";
      description
        "'bgp long-lived-graceful-restart stale-time
         (1-16777215)'.";
    }

    container graceful-restart {
      description
        "Per-instance graceful-restart configuration; each timer is
         mutually exclusive with its process-wide twin.";
      leaf mode {
        type enumeration {
          enum restarter {
            description
              "'bgp graceful-restart'.";
          }
          enum disable {
            description
              "'bgp graceful-restart-disable'.";
          }
        }
        description
          "Unset means FRR's default (helper mode).";
      }
      leaf notification {
        type boolean;
        description
          "'bgp graceful-restart notification <enabled|disabled>'
           (also 'no bgp graceful-restart notification
           <enabled|disabled>' to unset; RFC 8538 N-bit), emitted
           by bgp_config_write() in bgpd/bgp_vty.c. Tri-state: no
           YANG default, unset means the compile-profile default
           (FRR_CFG_DEFAULT_BOOL(BGP_GRACEFUL_NOTIFICATION), on from
           FRR 8.3 on); an explicit value, once set, is always
           rendered explicitly. Deprecated bare 'bgp graceful-restart
           notification' / 'no bgp graceful-restart notification'
           aliases keep loading configs saved before this leaf grew
           the enabled|disabled grammar (bare means true, bare 'no'
           persists an explicit false).";
      }
      leaf preserve-fw-state {
        type boolean;
        default "false";
        description
          "'bgp graceful-restart preserve-fw-state'.";
      }
      leaf restart-time {
        type uint16 {
          range "0..4095";
        }
        units "seconds";
      }
      leaf stalepath-time {
        type uint16 {
          range "1..4095";
        }
        units "seconds";
      }
      leaf select-defer-time {
        type uint16 {
          range "0..3600";
        }
        units "seconds";
      }
      leaf rib-stale-time {
        type uint16 {
          range "1..3600";
        }
        units "seconds";
      }
      leaf eor {
        type boolean;
        default "true";
        description
          "'bgp graceful-restart eor <enabled|disabled>' (hidden
           command): when enabled, the End-of-RIB marker is sent to
           peers; when disabled, it is never sent (default enabled).";
      }
    }

    container tcp-keepalive {
      must "not(idle or interval or probes)
            or (idle and interval and probes)" {
        error-message
          "'bgp tcp-keepalive' takes idle, interval and probes
           together";
      }
      description
        "'bgp tcp-keepalive (1-65535) (1-65535) (1-30)': TCP
         keepalive idle time, interval and probe count for BGP
         sessions. All three set together -- one CLI line (the
         'must').";
      leaf idle {
        type uint16 {
          range "1..65535";
        }
        units "seconds";
      }
      leaf interval {
        type uint16 {
          range "1..65535";
        }
        units "seconds";
      }
      leaf probes {
        type uint8 {
          range "1..30";
        }
      }
    }

    container bestpath {
      description
        "'bgp bestpath ...' route selection tuning.";
      leaf as-path-ignore {
        type boolean;
        default "false";
        description
          "'bgp bestpath as-path ignore'.";
      }
      leaf as-path-confed {
        type boolean;
        default "false";
        description
          "'bgp bestpath as-path confed'.";
      }
      container as-path-multipath-relax {
        description
          "'bgp bestpath as-path multipath-relax [as-set]'.";
        leaf enabled {
          type boolean;
          default "false";
        }
        leaf as-set {
          type boolean;
          default "false";
        }
      }
      leaf compare-routerid {
        type boolean;
        default "false";
        description
          "'bgp bestpath compare-routerid'.";
      }
      leaf use-imported-attributes {
        type boolean;
        default "false";
        description
          "'bgp bestpath use-imported-attributes': compare imported
           routes on their own attributes, not the originals'.";
      }
      leaf aigp {
        type boolean;
        description
          "'[no] bgp bestpath aigp' (default off; both forms may be
           written depending on the compile profile).";
      }
      container med {
        description
          "'bgp bestpath med [confed] [missing-as-worst]'.";
        leaf confed {
          type boolean;
          default "false";
        }
        leaf missing-as-worst {
          type boolean;
          default "false";
        }
      }
      leaf peer-type-multipath-relax {
        type boolean;
        default "false";
        description
          "'bgp bestpath peer-type multipath-relax': allow eBGP and
           iBGP paths in one multipath.";
      }
      leaf bandwidth {
        type enumeration {
          enum ignore {
            description
              "'bgp bestpath bandwidth ignore'.";
          }
          enum skip-missing {
            description
              "'bgp bestpath bandwidth skip-missing'.";
          }
          enum default-weight-for-missing {
            description
              "'bgp bestpath bandwidth
               default-weight-for-missing'.";
          }
        }
        description
          "Link-bandwidth handling for weighted ECMP; unset means
           FRR's default (skip paths with missing bandwidth from
           weighting).";
      }
    }

    leaf route-reflector-allow-outbound-policy {
      type boolean;
      description
        "'[no] bgp route-reflector allow-outbound-policy' (default
         off).";
    }

    leaf network-import-check {
      type boolean;
      description
        "'[no] bgp network import-check': require 'network'
         prefixes to exist in the RIB (profile-dependent
         default).";
    }

    container timers {
      description
        "Instance-wide default session timers.";
      leaf keepalive {
        type uint16;
        units "seconds";
        description
          "'timers bgp (0-65535) (0-65535)', first argument (FRR
           default 60). Set together with holdtime.";
      }
      leaf holdtime {
        type uint16;
        units "seconds";
        description
          "'timers bgp', second argument (FRR default 180).";
      }
      leaf minimum-holdtime {
        type uint16 {
          range "1..65535";
        }
        units "seconds";
        description
          "'bgp minimum-holdtime (1-65535)': reject peers offering
           less.";
      }
      leaf conditional-advertisement {
        type uint8 {
          range "5..240";
        }
        units "seconds";
        description
          "'bgp conditional-advertisement timer (5-240)': scanner
           period for advertise-map conditions.";
      }
      leaf default-originate {
        type uint16;
        units "seconds";
        description
          "'bgp default-originate timer (0-65535)': re-evaluation
           period for default-originate route-maps.";
      }
    }

    list peer-group {
      key "name";
      description
        "'neighbor PGNAME peer-group' declaration plus everything
         configured on the group. Members inherit any session or
         per-AF setting they don't override themselves -- FRR
         writes only the overrides back, but in this model each
         node simply holds what the user set where they set it.";

      leaf name {
        type string {
          length "1..max";
        }
      }

      uses neighbor-session-parameters;

      leaf-list listen-range {
        type union {
          type inet:ipv4-prefix;
          type inet:ipv6-prefix;
        }
        description
          "'bgp listen range <A.B.C.D/M|X:X::X:X/M> peer-group
           PGNAME': accept dynamic neighbors from these prefixes
           into this group (bgp_config_write_listen in
           bgpd/bgp_vty.c; written at instance level but owned by
           the group).";
      }

      container afi-safis {
        description
          "Per-address-family settings of the peer-group; same
           shape as a neighbor's.";
        container ipv4-unicast {
          uses neighbor-af;
          uses neighbor-af-filters-ipv4;
          uses neighbor-af-encap-unicast;
        }
        container ipv4-multicast {
          uses neighbor-af;
          uses neighbor-af-filters-ipv4;
        }
        container ipv4-labeled-unicast {
          uses neighbor-af;
          uses neighbor-af-filters-ipv4;
        }
        container ipv4-vpn {
          uses neighbor-af;
          uses neighbor-af-filters-ipv4;
          uses neighbor-af-encap-vpn;
        }
        container ipv6-unicast {
          uses neighbor-af;
          uses neighbor-af-filters-ipv6;
          uses neighbor-af-encap-unicast;
        }
        container ipv6-multicast {
          uses neighbor-af;
          uses neighbor-af-filters-ipv6;
        }
        container ipv6-labeled-unicast {
          uses neighbor-af;
          uses neighbor-af-filters-ipv6;
        }
        container ipv6-vpn {
          uses neighbor-af;
          uses neighbor-af-filters-ipv6;
          uses neighbor-af-encap-vpn;
        }
        container ipv4-flowspec {
          uses neighbor-af-flowspec;
        }
        container ipv4-unreachability {
          uses neighbor-af-unreachability;
        }
        container ipv6-flowspec {
          uses neighbor-af-flowspec;
        }
        container ipv6-unreachability {
          uses neighbor-af-unreachability;
        }
        container l2vpn-evpn {
          uses neighbor-af;
          uses neighbor-af-filters-evpn;
        }
        container link-state {
          uses neighbor-af-link-state;
        }
      }
    }

    list neighbor {
      key "address";
      must "remote-as/plain or remote-as/asdot/high or remote-as/type
            or peer-group" {
        error-message
          "a neighbor needs remote-as, directly or via its
           peer-group";
      }
      description
        "One BGP peer: its session-level 'neighbor X ...' lines
         plus per-address-family blocks. remote-as must come from
         the neighbor itself or its peer-group (the 'must',
         spelled against remote-as's choice members since an
         all-empty container always 'exists' -- the
         conditional-mandatory rule the shared remote-as node
         cannot state). Bare peer-group membership satisfies it
         even when the group itself has no remote-as: legacy
         retains such members in Active ('no neighbor PG
         remote-as' keeps the members, they just cannot
         establish).";

      leaf address {
        type union {
          type inet:ip-address-no-zone;
          // Interface-name branch: lax leafref (require-instance false) per
          // the C.4 test (libyang, 2026-07-19) - kernel interfaces without
          // an 'interface' config stanza must remain accepted.
          type leafref {
            path "/frr-interface:lib/frr-interface:interface/frr-interface:name";
            require-instance false;
          }
        }
        description
          "Peer IPv4/IPv6 address, or an interface name for
           unnumbered interface peers (set interface-peer below).
           The interface-name branch is a lax leafref
           (require-instance false): unnumbered peers name kernel
           interfaces that need no 'interface' config stanza, and
           those must remain acceptable.";
      }

      leaf interface-peer {
        type boolean;
        default "false";
        description
          "'neighbor IFNAME interface [v6only] ...': address is an
           interface name; the session runs unnumbered over its
           link-local (RFC 5549).";
      }
      leaf v6only {
        type boolean;
        default "false";
        description
          "The v6only token of the interface form: never use the
           interface's IPv4 address.";
      }

      leaf peer-group {
        type leafref {
          path "../../peer-group/name";
        }
        description
          "'neighbor X peer-group PGNAME': inherit the group's
           configuration.";
      }

      uses neighbor-session-parameters;

      container afi-safis {
        description
          "This neighbor's per-address-family settings; one
           container per family, rendered inside the matching
           'address-family ...' block.";

        container ipv4-unicast {
          uses neighbor-af;
          uses neighbor-af-filters-ipv4;
          uses neighbor-af-encap-unicast;
        }
        container ipv4-multicast {
          uses neighbor-af;
          uses neighbor-af-filters-ipv4;
        }
        container ipv4-labeled-unicast {
          uses neighbor-af;
          uses neighbor-af-filters-ipv4;
        }
        container ipv4-vpn {
          uses neighbor-af;
          uses neighbor-af-filters-ipv4;
          uses neighbor-af-encap-vpn;
        }
        container ipv6-unicast {
          uses neighbor-af;
          uses neighbor-af-filters-ipv6;
          uses neighbor-af-encap-unicast;
        }
        container ipv6-multicast {
          uses neighbor-af;
          uses neighbor-af-filters-ipv6;
        }
        container ipv6-labeled-unicast {
          uses neighbor-af;
          uses neighbor-af-filters-ipv6;
        }
        container ipv6-vpn {
          uses neighbor-af;
          uses neighbor-af-filters-ipv6;
          uses neighbor-af-encap-vpn;
        }
        container ipv4-flowspec {
          uses neighbor-af-flowspec;
        }
        container ipv4-unreachability {
          uses neighbor-af-unreachability;
        }
        container ipv6-flowspec {
          uses neighbor-af-flowspec;
        }
        container ipv6-unreachability {
          uses neighbor-af-unreachability;
        }
        container l2vpn-evpn {
          description
            "Neighbor settings under 'address-family l2vpn evpn' --
             the same per-AF knob set as every other family (FRR
             simply doesn't emit the meaningless ones there).";
          uses neighbor-af;
          uses neighbor-af-filters-evpn;
        }
        container link-state {
          uses neighbor-af-link-state;
        }
      }
    }

    leaf listen-limit {
      type uint16 {
        range "1..65535";
      }
      description
        "'bgp listen limit (1-65535)': cap on dynamic
         (listen-range) neighbors.";
    }

    container administrative-shutdown {
      description
        "Administrative shutdown of the whole instance.";
      leaf enabled {
        type boolean;
        default "false";
        description
          "'bgp shutdown': administratively shut the whole
           instance -- every peer session is held down until
           re-enabled.";
      }
      leaf message {
        type string {
          length "1..255";
        }
        description
          "'bgp shutdown message MSG...': sent to every peer in
           the CEASE/Administrative Shutdown notification (RFC
           9003) when the shutdown takes effect.";
      }
    }

    leaf allow-martian-nexthop {
      type boolean;
      default "false";
      description
        "'bgp allow-martian-nexthop'.";
    }

    leaf use-underlays-nexthop-weight {
      type boolean;
      default "false";
      description
        "'use-underlays-nexthop-weight': weight ECMP paths by
         the resolved (recursive) nexthops' own weights instead
         of link-bandwidth-derived values.";
    }

    leaf fast-convergence {
      type boolean;
      default "false";
      description
        "'bgp fast-convergence': drop sessions immediately on
         link-down.";
    }

    container afi-safis {
      description
        "Instance-level per-address-family configuration
         ('address-family ... / exit-address-family' blocks); one
         container per family.
         // Not modeled: ipv4/ipv6 encap, flowspec, unreachability
         // and link-state families (see module description).";

      container ipv4-unicast {
        description
          "'address-family ipv4 unicast'.";
        uses af-network-ipv4;
        uses af-aggregate-ipv4;
        uses af-redistribute;
        uses af-route-selection;
        uses af-distance-ipv4;
        uses af-vpn-leaking;
        uses af-srv6-sid-export;
      }

      container ipv4-multicast {
        description
          "'address-family ipv4 multicast'.";
        uses af-network-ipv4;
        uses af-aggregate-ipv4;
        uses af-route-selection;
        uses af-distance-ipv4;
      }

      container ipv4-labeled-unicast {
        description
          "'address-family ipv4 labeled-unicast'.";
        uses af-network-ipv4;
        uses af-aggregate-ipv4;
        uses af-route-selection;
        uses af-distance-ipv4;
      }

      container ipv4-vpn {
        description
          "'address-family ipv4 vpn'.";
        uses af-network-vpn-ipv4;
        uses af-route-selection;
        uses af-distance-ipv4;
        uses af-retain-route-target;
      }

      container ipv4-flowspec {
        description
          "'address-family ipv4 flowspec' (M8.5 B-fs-af).
           Default-instance-only (legacy address_family arms reject
           non-default instances). Instance-level content arrives in
           B-fs-extras (local-install).";
      
        container local-install {
          presence
            "'local-install INTERFACE' is configured (or the
             interface-any default was explicitly overridden).";
          description
            "'[no] local-install INTERFACE' (bgp_fs_local_install_
             interface): restrict flowspec rule installation to the
             listed interfaces. Also models the previously
             unpersistable any=false-with-empty-list state via
             interface-any.";

          leaf interface-any {
            type boolean;
            default "true";
            description
              "Install flowspec rules on any interface. Forced
               false while the interfaces list is non-empty.";
          }

          leaf-list interfaces {
            // Interface-name branch: lax leafref (require-instance false) per
            // the C.4 test (libyang, 2026-07-19) - kernel interfaces without
            // an 'interface' config stanza must remain accepted.
            type leafref {
              path "/frr-interface:lib/frr-interface:interface/frr-interface:name";
              require-instance false;
            }
            description
              "Interfaces to install flowspec rules on.";
          }
        }
      }

      container ipv6-unicast {
        description
          "'address-family ipv6 unicast'.";
        uses af-network-ipv6;
        uses af-aggregate-ipv6;
        uses af-redistribute;
        uses af-route-selection;
        uses af-distance-ipv6;
        uses af-vpn-leaking;
        uses af-srv6-sid-export;
        leaf nexthop-prefer-global {
          type boolean;
          description
            "'[no] nexthop prefer-global': prefer the global IPv6
             next hop over the link-local
             (bgp_config_write_ipv6_nexthop_prefer_global).";
        }
      }

      container ipv6-multicast {
        description
          "'address-family ipv6 multicast'.";
        uses af-network-ipv6;
        uses af-aggregate-ipv6;
        uses af-route-selection;
        uses af-distance-ipv6;
        leaf nexthop-prefer-global {
          type boolean;
          description
            "'[no] nexthop prefer-global': prefer the global IPv6
             next hop over the link-local
             (bgp_config_write_ipv6_nexthop_prefer_global).";
        }
      }

      container ipv6-labeled-unicast {
        description
          "'address-family ipv6 labeled-unicast'.";
        uses af-network-ipv6;
        uses af-aggregate-ipv6;
        uses af-route-selection;
        uses af-distance-ipv6;
        leaf nexthop-prefer-global {
          type boolean;
          description
            "'[no] nexthop prefer-global': prefer the global IPv6
             next hop over the link-local
             (bgp_config_write_ipv6_nexthop_prefer_global).";
        }
      }

      container ipv6-vpn {
        description
          "'address-family ipv6 vpn'.";
        uses af-network-vpn-ipv6;
        uses af-route-selection;
        uses af-distance-ipv6;
        uses af-retain-route-target;
      }

      container ipv4-unreachability {
        description
          "'address-family ipv4 unreachability' (M9). No
           instance-level knobs: maximum-paths is pinned to 1 for
           the informational unreachability RIB and the legacy node
           installed only per-neighbor commands.";
      }

      container ipv6-flowspec {
        description
          "'address-family ipv6 flowspec' (M8.5 B-fs-af).";
      
        container local-install {
          presence
            "'local-install INTERFACE' is configured.";
          description
            "See ipv4-flowspec/local-install.";

          leaf interface-any {
            type boolean;
            default "true";
          }

          leaf-list interfaces {
            // Interface-name branch: lax leafref (require-instance false) per
            // the C.4 test (libyang, 2026-07-19) - kernel interfaces without
            // an 'interface' config stanza must remain accepted.
            type leafref {
              path "/frr-interface:lib/frr-interface:interface/frr-interface:name";
              require-instance false;
            }
          }
        }
      }

      container ipv6-unreachability {
        description
          "'address-family ipv6 unreachability' (M9). See
           ipv4-unreachability.";
      }

      container l2vpn-evpn {
        description
          "'address-family l2vpn evpn'. Field definitions live in
           proteus-bgp-evpn.yang.";
        uses evpn:instance-l2vpn-evpn;
      }

      container link-state {
        description
          "'address-family link-state link-state' (M9, RFC 9552).";

        container distribute-bgp-fabric-link-state {
          presence
            "'distribute bgp-fabric-link-state [instance-id WORD]'
             is configured: export the BGP fabric topology as BGP-LS
             NLRIs.";
          description
            "Distribute BGP link-state topology information.";

          leaf instance-id {
            type uint64;
            description
              "BGP-LS instance identifier; absent means 0 (and 0 is
               not written back).";
          }
        }
      }
    }
  }

  /*
   * bgpd's interface-level settings. The 'interface NAME' block itself
   * is frr-interface's surface (lib/if.c owns the list and its CLI);
   * bgpd only contributes these two flags, so they hang off
   * frr-interface's interface list as an augment, the same way zebra's
   * interface knobs do (frr-zebra.yang), instead of living in a
   * standalone interface module.
   */
  augment "/frr-interface:lib/frr-interface:interface" {
    description
      "Extends the interface model with bgpd's interface-level
       parameters: the two 'mpls bgp ...' flags (DEFPYs installed at
       INTERFACE_NODE, written back inside the 'interface NAME'
       block).";
    container bgp {
      description
        "BGP interface parameters.";

      leaf mpls-bgp-forwarding {
        type boolean;
        default "false";
        description
          "'mpls bgp forwarding': enable MPLS forwarding for directly
           connected eBGP peers on this interface. Only the positive
           form is ever written back.";
      }

      leaf mpls-bgp-l3vpn-multi-domain-switching {
        type boolean;
        default "false";
        description
          "'mpls bgp l3vpn-multi-domain-switching': bind a local MPLS
           label to incoming L3VPN updates (inter-AS option B /
           multi-domain). Only the positive form is ever written
           back.";
      }
    }
  }
}
